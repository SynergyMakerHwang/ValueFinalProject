' Sub to update a object in part'
Sub UpdateObjectErr(activepart,objecttoupdate,strErrAdd)
  activepart.InWorkObject = objecttoupdate
  On Error Resume Next
  activepart.UpdateObject(objecttoupdate)
  if Err.Number<>0 then
    SaveErrNum=Err.Number
    SaveErrDesc=Err.Description & ": " & vbCrLf & strErrAdd
    SaveErrHCon=Err.HelpContext
    SaveErrHFil=Err.HelpFile
    SaveErrSour=Err.Source
    On Error Goto 0
    Err.Raise SaveErrNum,SaveErrSour,SaveErrDesc,SaveErrHFil,SaveErrHCon
  end if
  On Error Goto 0
End Sub

' Sub to update whole part'
Sub UpdatePartErr(activepart,strErrAdd)
  On Error Resume Next
  activepart.Update
  if Err.Number<>0 then
    SaveErrNum=Err.Number
    SaveErrDesc=Err.Description & ": " & vbCrLf & strErrAdd
    SaveErrHCon=Err.HelpContext
    SaveErrHFil=Err.HelpFile
    SaveErrSour=Err.Source
    On Error Goto 0
    Err.Raise SaveErrNum,SaveErrSour,SaveErrDesc,SaveErrHFil,SaveErrHCon
  end if
  On Error Goto 0
End Sub

Function GetNearestFaceReferenceByPoint(wpart, x, y, z)
  CATIA.HSOSynchronized = False
  CATIA.RefreshDisplay = False
  Set shapeFactory1 = wpart.ShapeFactory
  Set hybridShapeFactory1 = wpart.HybridShapeFactory
  Set Body = wpart.MainBody
  Set HybridBody1 = wPart.hybridBodies.item(1)
  set point = hybridShapeFactory1.AddNewPointCoord(x, y, z)
  HybridBody1.AppendHybridShape point 
  wpart.Update
  Set selection = CATIA.ActiveDocument.Selection
  selection.Clear
  selection.Search "Topology.CGMFace, all"
  set pointReference = wpart.CreateReferenceFromObject(point)
  set spaworkbench = CATIA.ActiveDocument.GetWorkbench("SPAWorkbench")
  set pointmeasure = spaworkbench.GetMeasurable(point)
  mindistance = 308000000
  set targetface = nothing
  for i = 1 to selection.Count
    distance = pointmeasure.GetMinimumDistance(selection.Item(i).Reference)
    if distance < mindistance then
      set targetface = selection.Item(i).Reference
      mindistance = distance
      if mindistance < 0.001 then exit for
    end if
  next
  selection.Clear
  selection.Add point
  selection.Delete
  Set GetNearestFaceReferenceByPoint = targetface
  CATIA.HSOSynchronized = True
  CATIA.RefreshDisplay = True
End Function

sub CreateFolder(sFolder)

	dim tmp1
	tmp1=replace(sfolder,"/",catia.FileSystem.FileSeparator)
	dim tmp2
	tmp2=replace(tmp1,"\",catia.FileSystem.FileSeparator)
	dim oShell
	Set oShell = CreateObject("WScript.Shell")
	sFolder=oShell.ExpandEnvironmentStrings(tmp2)
	dim fs
	set fs=createobject("Scripting.Filesystemobject")
	dim sAbsFolder
	sAbsFolder = fs.GetAbsolutePathName(sFolder)
	if not (fs.FolderExists(sAbsFolder)) then
		 CreateFolderRecursive(sAbsFolder)
	end if

end sub


sub CreateFolderRecursive(sFolder)

	dim fs
	set fs=createobject("Scripting.Filesystemobject")
	if not (fs.FolderExists(sFolder)) then
		CreateFolderRecursive fs.GetParentFolderName(sFolder)
		fs.CreateFolder(sFolder)
	end if

end sub

sub ApplyColors(arrSurf,arrSurfVal,arrPointmeasure,arrPointVal,arrR,arrG,arrB)
  dim i
  dim j
  for j = 0 to ubound(arrPointmeasure)
    set pointmeasure1 = arrPointmeasure(j)
    mindistance = 308000000
     set targetface = nothing
    for each surf1 in arrSurf
      distance = pointmeasure1.GetMinimumDistance(surf1)
      if distance < mindistance then
        mindistance = distance
        set targetface = surf1
      end if
    next
    if not(targetface is nothing) then
      CATIA.ActiveDocument.selection.clear
      CATIA.ActiveDocument.selection.add(targetface)
      CATIA.ActiveDocument.selection.VisProperties.SetRealColor arrR(j),arrG(j),arrB(j),1
      CATIA.ActiveDocument.selection.clear
    end if
  next

End sub

Dim storePath

' Sub to read the Store Path
Function ReadSPath()
  os = UCase(Left(CATIA.SystemConfiguration.OperatingSystem, 3))
  sep = "/"
  If (os = "WIN") Or (os = "INT") Then
    sep = "\"
  End If

  If (Len(storePath) = 0) Then
    ret = InputBox("Enter Path for CATPart or CATProduct (e.g. c:" + sep + "catfiles" + sep + ")", "Save as")
    storePath = ret
  End If

  Set fso = CreateObject("Scripting.FileSystemObject")

  If (Len(storePath) = 0) Or (fso.FolderExists(storePath) = False) Then
    Set fso = Nothing
    ReadSPath = Empty
    Exit Function
  End If

  If (Mid(storePath, Len(storePath), 1) <> sep) Then
    storePath = storePath + sep
  End If

  ReadSPath = storePath
  Set fso = Nothing
End Function

' Sub to store a document'
Sub SaveDocument(document, name)
  dim bSaveDFA
  bSaveDFA = CATIA.DisplayFileAlerts
  CATIA.DisplayFileAlerts = false
  document.SaveAs storePath & name
  CATIA.DisplayFileAlerts = bSaveDFA
End Sub

 Sub ProcessDocumentBeforeSave (document, name)
 If (TypeName(document) = "ProductDocument") Then
 Set partDocument1 = CATIA.ActiveDocument
 Set selection1 = partDocument1.Selection
 selection1.Search ("Name=AVL_WEIGHT,in")
 If (selection1.Count = 1) Then
   selection1.Clear
   selection1.Search ("(Name=Masse + Name=Mass);in")
 Set measure_inertia =selection1.Item(1)
 catia.StartCommand ("MeasureUpdate")
 End If
 ElseIf (TypeName(document) = "PartDocument") Then
 Set partDocument1 = CATIA.ActiveDocument
 Set selection1 = partDocument1.Selection
 Set partDocument1 = CATIA.ActiveDocument
 Set selection1 = partDocument1.Selection
 selection1.Search ("Name=AVL_WEIGHT,in")
 If (selection1.Count = 1) Then
 selection1.Clear
 selection1.Search ("(Name=Masse + Name=Mass);in")'
 Set part1 = partDocument1.Part
 Set measure_inertia =selection1.Item(1)
 partDocument1.Part.UpdateObject (measure_inertia.Value)
 End If
 End If
End Sub

' Sub to export a document'
Sub ExportDocument(document, name, format)
  document.ExportData storePath & name, format
End Sub

' Sub to retrieve a name in capital letters'
Function GetUCaseName(name)
  ucaseName = Left(name, InStrRev(name, ".") - 1)
  extension = Right(name, Len(name) - InStr(name, ".") + 1)
  GetUCaseName = UCase(ucaseName) + extension
End Function

Function GetBrep(SelectionToBRepDisplayName As String) As String
  MyBRepName = Replace(SelectionToBRepDisplayName, "Selection_", "")
  MyBRepName = Left(MyBRepName, InStrRev(MyBRepName, "));"))
  MyBRepName = MyBRepName + ");WithTemporaryBody;WithoutBuildError;WithDefaultFeatureSupport;MonoFond;MFBRepVersion_CXR15)"
  GetBrep = MyBRepName
End Function

Function GetFaceEdgeSelections(document, faceSelection)
  searchStr = faceSelection.Reference.DisplayName
  searchStr = Mid(searchStr, InStr(searchStr, "Brp:"))
  catiaRelease = CATIA.SystemConfiguration.Release
  if (catiaRelease < 30) Then
    searchStr = Left(searchStr, InStr(searchStr, "Cf11:()") + 6)
  ElseIf  ((catiaRelease = 30) or (catiaRelease = 31)) Then 
    searchStr = Left(searchStr, InStr(searchStr, "Cf12:()") + 6)
  ElseIf (catiaRelease = 32) Then 
    searchStr = Left(searchStr, InStr(searchStr, "Cf14:()") + 6)
  End If
  Set selection = document.Selection
  selection.Clear
  selection.Search "Topology.CGMEdge, all"
  Dim edgeArr(1000)
  i = 1
  For j = 1 To selection.Count
    Set selEdge = selection.Item2(j)
    edgeRef = selEdge.Reference.DisplayName
    If (InStr(edgeRef, searchStr)) Then
      Set edgeArr(i) = selEdge
      i = i + 1
    End If
  Next
  edgeArr(0) = i - 1
  GetFaceEdgeSelections = edgeArr
  selection.Clear
End Function

Function GetFaceFaceEdgeSelections(document, faceSelection1, faceSelection2)
  searchStr1 = faceSelection1.Reference.DisplayName
  searchStr1 = Mid(searchStr1, InStr(searchStr1, "Brp:"))
  catiaRelease = CATIA.SystemConfiguration.Release
  if (catiaRelease < 30) Then
    searchStr1 = Left(searchStr1, InStr(searchStr1, "Cf11:()") + 6)
  ElseIf  ((catiaRelease = 30) or (catiaRelease = 31)) Then 
    searchStr1 = Left(searchStr1, InStr(searchStr1, "Cf12:()") + 6)
  ElseIf (catiaRelease = 32) Then 
    searchStr1 = Left(searchStr1, InStr(searchStr1, "Cf14:()") + 6)
  End If
  searchStr2 = faceSelection2.Reference.DisplayName
  searchStr2 = Mid(searchStr2, InStr(searchStr2, "Brp:"))
  if (catiaRelease < 30) Then
    searchStr2 = Left(searchStr2, InStr(searchStr2, "Cf11:()") + 6)
  ElseIf  ((catiaRelease = 30) or (catiaRelease = 31)) Then 
    searchStr2 = Left(searchStr2, InStr(searchStr2, "Cf12:()") + 6)
  ElseIf (catiaRelease = 32) Then 
    searchStr2 = Left(searchStr2, InStr(searchStr2, "Cf14:()") + 6)
  End If
  Set selection = document.Selection
  selection.Clear
  selection.Search "Topology.CGMEdge, all"
  Dim edgeArr(1000)
  i = 1
  For j = 1 To selection.Count
    Set selEdge = selection.Item2(j)
    edgeRef = selEdge.Reference.DisplayName
    If (InStr(edgeRef, searchStr1) And InStr(edgeRef, searchStr2)) Then
      Set edgeArr(i) = selEdge
      i = i + 1
    End If
  Next
  edgeArr(0) = i - 1
  GetFaceFaceEdgeSelections = edgeArr
  selection.Clear
End Function

  Function GetFaceReferenceByPoint(document, wpart, bodycurrent, x, y, z,nx,ny,nz,eps,isfaceconic)
    Set shapeFactory1 = wpart.ShapeFactory
    Set hybridShapeFactory1 = wpart.HybridShapeFactory
    Set Body = wpart.MainBody
    Set Point = hybridShapeFactory1.AddNewPointCoord(x, y, z)
     Set HybridBody1 = wPart.hybridBodies.item(1)
     HybridBody1.AppendHybridShape Point
     UpdateObjectErr wPart, Point, wPart.name & "/" & HybridBody1.name & "/" & Point.name
    Set Selection = document.Selection
    Selection.Clear
    Selection.Add(bodycurrent)
    Selection.Search ("Topology.CGMFace, sel")
    Set pointReference = wpart.CreateReferenceFromObject(Point)
    Set SPAWorkbench = document.GetWorkbench("SPAWorkbench")
    Set pointmeasure = SPAWorkbench.GetMeasurable(Point)
    mindistance = eps
    Set targetface1 = Nothing
    Set targetReferenceface1 = Nothing
    Set faceSelection = Nothing
    Set facereference = Nothing
    Set Face = Nothing
    Dim varCATSafeArrayVariant(3) As Variant
    Dim dir1(3) As Variant
    Dim dir2(3) As Variant
    Dim i,k,facelist()
    k = 0
    For i = 1 To Selection.Count
      Set faceSelection = Selection.Item(i)
      Set facereference = faceSelection.Reference
      Set Face = faceSelection.Value
      validface = False
      If faceSelection.Type = "PlanarFace" Then
        Face.GetFirstAxis (dir1)
        Face.GetSecondAxis (dir2)
        varCATSafeArrayVariant(0) = dir1(1) * dir2(2) - dir1(2) * dir2(1)
        varCATSafeArrayVariant(1) = dir1(2) * dir2(0) - dir1(0) * dir2(2)
        varCATSafeArrayVariant(2) = dir1(0) * dir2(1) - dir1(1) * dir2(0)
        validFace = True
      ElseIf faceSelection.Type = "CylindricalFace" Then
        Face.GetDirection (varCATSafeArrayVariant)
        validface = True
      Else
        k = k+1
        redim preserve facelist(k)
        set facelist(k) = facereference
      End If
      If validface Then
        sk = Abs(varCATSafeArrayVariant(0) * nx + varCATSafeArrayVariant(1) * ny + varCATSafeArrayVariant(2) * nz)
        If sk > 1 - 0.00001 Then
          Distance = pointmeasure.GetMinimumDistance(facereference)
          If Distance < mindistance Then
            Set targetface1 = faceSelection
            Set targetReferenceface1 = facereference
            mindistance = Distance
          End If
        End If
      End If
    Next
    if  targetReferenceface1 is nothing then
      for i = 1 to k
       set faceconic = facelist (i)
    	  Set facemeasure = SPAWorkbench.GetMeasurable(faceconic)
    	  If facemeasure.GeometryName = "6" Then
    	     Distance = pointmeasure.GetMinimumDistance(faceconic)
    	     If Distance < eps Then
    		    Set targetReferenceface1 = faceconic
    		    Set GetFaceReferenceByPoint = targetReferenceface1
    		    isfaceconic  = 1
    		    Selection.Clear
           Selection.Add (Point)
           Selection.Delete
    	      Exit Function
    	   End If
    	  End If
      next
    end if
    Selection.Clear
    Selection.Add (Point)
    Selection.Delete
    Set GetFaceReferenceByPoint = targetReferenceface1
  End Function
' Sub to publish a object in part'
Sub PublishInPart(oPart, oToPublish)
  Dim oHS1,oHB1,prod1,pubs1,sPubName,refProd1,pub1 
  set oHS1 = oToPublish.Parent
  set oHB1 = oHS1.Parent
  set prod1 = oPart.Parent.product
  set pubs1 = prod1.Publications
  sPubName = oToPublish.Name
  sPubName = Replace(sPubName, "!", "_")
  sPubName = Replace(sPubName, ":", "_")
  sPubName = Replace(sPubName, "<", "_")
  sPubName = Replace(sPubName, ">", "_")
  sPubName = Replace(sPubName, " ", "_")
  set refProd1 = prod1.CreateReferenceFromName(prod1.PartNumber & "/!" & oHB1.Name & "/" & oToPublish.Name)
  set pub1 = pubs1.Add(sPubName)
  pubs1.SetDirect sPubName, refProd1
End Sub

Function GetFirstInstanceName(strSearchedName , oProducts )
		Dim strTmp As String
		strTmp = ""
		Dim i
		For i = 1 To 100
				strTmp = strSearchedName & "." & CStr(i)

				On Error Resume Next

				oProducts.Item(strTmp)
				If Err.Number <> 0 Then
						Err.Clear()
            On Error GoTo 0
						Exit For
				End If

				On Error GoTo 0

		Next
		GetFirstInstanceName = strTmp
End Function

sub GetMaterialFromCatalog(strPathCATMaterialFile, strMaterialName, iFamilyOut, iMaterialOut)
  iFamilyOut = 0
  iMaterialOut = 0

 'Check if CATMaterial file Exists
  if (not (CATIA.FileSystem.FileExists(strPathCATMaterialFile) )) then
    Exit sub
  End if

  Dim oMaterial_document
  set oMaterial_document = Nothing

  Set oMaterial_document = CATIA.Documents.Read(strPathCATMaterialFile)
  if (not (oMaterial_document is Nothing)) then

    'Get Material Families From Document
    Dim i
    Dim objFamily
    Dim objCurrentMaterial
    Dim strCurrentMaterialName
    For i = 1 to  oMaterial_document.Families.Count
      'Get current material Family
      set objFamily = oMaterial_document.Families.Item(i)
      Dim j
      For j = 1 to objFamily.Materials.Count
        'Get current material
        set objCurrentMaterial = objFamily.Materials.Item(j)
        strCurrentMaterialName = objCurrentMaterial.Name
        if strCurrentMaterialName = strMaterialName then
          iMaterialOut = j
          iFamilyOut = i
          oMaterial_document.Close
          Exit sub
        End if

      Next

    Next
    oMaterial_document.Close
  end if

End sub

Function toolCall0(wpart,HybridBody1)
  set backWork = wPart.InWorkObject 
  UpdateObjectErr wPart, HybridBody1, wPart.name & "/" & HybridBody1.name
  Set hypFact = wPart.HybridShapeFactory
  Set HybridShapePointCoord0 = hypFact.AddNewPointCoord(0, 0, 0)
  HybridBody1.AppendHybridShape HybridShapePointCoord0
  UpdateObjectErr wPart, HybridShapePointCoord0, wPart.name & "/" & HybridBody1.name & "/" & HybridShapePointCoord0.name
  Set HybridShapePointCoord1 = hypFact.AddNewPointCoord(0, 0, -1)
  HybridBody1.AppendHybridShape HybridShapePointCoord1
  UpdateObjectErr wPart, HybridShapePointCoord1, wPart.name & "/" & HybridBody1.name & "/" & HybridShapePointCoord1.name
  Set HybridShapePointCoord2 = hypFact.AddNewPointCoord(0, 1, 0)
  HybridBody1.AppendHybridShape HybridShapePointCoord2
  UpdateObjectErr wPart, HybridShapePointCoord2, wPart.name & "/" & HybridBody1.name & "/" & HybridShapePointCoord2.name
  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  UpdateObjectErr wPart, absPlane, wPart.name & "/" & HybridBody1.name & "/" & absPlane.name
  Set absRef = wPart.CreateReferenceFromGeometry(absPlane)

  Set datpoint1 = hypFact.AddNewPointDatum(Reference0)
  HybridBody1.AppendHybridShape datpoint1
  Set datpoint2 = hypFact.AddNewPointDatum(Reference1)
  HybridBody1.AppendHybridShape datpoint2
  Set datpoint3 = hypFact.AddNewPointDatum(Reference2)
  HybridBody1.AppendHybridShape datpoint3
  Set datplane1 = hypFact.AddNewPlaneDatum(absRef)
  HybridBody1.AppendHybridShape datplane1

  hypFact.DeleteObjectForDatum Reference0
  hypFact.DeleteObjectForDatum Reference1
  hypFact.DeleteObjectForDatum Reference2
  hypFact.DeleteObjectForDatum absRef

  Set absdatRef = wPart.CreateReferenceFromGeometry(datplane1)

  UpdatePartErr wPart, wPart.name & "/" & HybridBody1.name
  wPart.InWorkObject = backWork
  Set toolCall0=absdatRef
End Function

Function toolCall1(wpart,body,absref)
  UpdateObjectErr wPart, Body, wPart.name & "/" & Body.name
  Set sketch = Body.Sketches.Add(absRef)
  CATIA.ActiveDocument.Selection.Clear
  CATIA.ActiveDocument.Selection.Add(sketch)
  CATIA.ActiveDocument.Selection.VisProperties.SetShow(1)
  CATIA.ActiveDocument.Selection.Clear

  Set factory2d = sketch.OpenEdition
  Set Axis2D7 = Sketch.AbsoluteAxis
  Set Line2D8 = Axis2D7.HorizontalReference
  Line2D8.ReportName = 1
  Set Line2D9 = Axis2D7.VerticalReference
  Line2D9.ReportName = 2
  Set constraints1 = Sketch.Constraints

  Set startPoint = Factory2D.CreatePoint(-29, 0)
  Set endPoint = Factory2D.CreatePoint(-29, 23.7)
  Set line = factory2d.CreateLine(-29, 0, -29, 23.7)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-29, 23.7)
  Set endPoint = Factory2D.CreatePoint(-28.7, 24)
  Set line = factory2d.CreateLine(-29, 23.7, -28.7, 24)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-28.7, 24)
  Set endPoint = Factory2D.CreatePoint(-15, 24)
  Set line = factory2d.CreateLine(-28.7, 24, -15, 24)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-15, 24)
  Set endPoint = Factory2D.CreatePoint(-15, 30)
  Set line = factory2d.CreateLine(-15, 24, -15, 30)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-15, 30)
  Set endPoint = Factory2D.CreatePoint(-13.1243556529822, 37)
  Set line = factory2d.CreateLine(-15, 30, -13.1243556529822, 37)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-13.1243556529822, 37)
  Set endPoint = Factory2D.CreatePoint(-1.87564434701785, 37)
  Set line = factory2d.CreateLine(-13.1243556529822, 37, -1.87564434701785, 37)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-1.87564434701785, 37)
  Set endPoint = Factory2D.CreatePoint(0, 30.0000000000001)
  Set line = factory2d.CreateLine(-1.87564434701785, 37, 0, 30.0000000000001)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(0, 30.0000000000001)
  Set endPoint = Factory2D.CreatePoint(0, 0)
  Set line = factory2d.CreateLine(0, 30.0000000000001, 0, 0)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(0, 0)
  Set endPoint = Factory2D.CreatePoint(-29, 0)
  Set line = factory2d.CreateLine(0, 0, -29, 0)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set pk1 = Factory2D.CreatePoint(500, 0)
  Set pk2 = Factory2D.CreatePoint(-500, 0)
  Set line = Factory2d.CreateLine(500, 0, -500, 0)
  sketch.CenterLine = line
  Set ref1 = wpart.CreateReferenceFromObject(pk1)
  Set ref2 = wpart.CreateReferenceFromObject(pk2)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Sketch.CloseEdition
  UpdateObjectErr wpart, Sketch, wPart.name & "/" & Body.name & "/" & Sketch.name
  Set sketch4 = sketch
  Set toolCall1=sketch4
End Function

Function toolCall2(wpart,HybridBody1)
  set backWork = wPart.InWorkObject 
  UpdateObjectErr wPart, HybridBody1, wPart.name & "/" & HybridBody1.name
  Set hypFact = wPart.HybridShapeFactory
  Set HybridShapePointCoord0 = hypFact.AddNewPointCoord(0, 0, 0)
  HybridBody1.AppendHybridShape HybridShapePointCoord0
  UpdateObjectErr wPart, HybridShapePointCoord0, wPart.name & "/" & HybridBody1.name & "/" & HybridShapePointCoord0.name
  Set HybridShapePointCoord1 = hypFact.AddNewPointCoord(1, 0, 0)
  HybridBody1.AppendHybridShape HybridShapePointCoord1
  UpdateObjectErr wPart, HybridShapePointCoord1, wPart.name & "/" & HybridBody1.name & "/" & HybridShapePointCoord1.name
  Set HybridShapePointCoord2 = hypFact.AddNewPointCoord(0, 1, 0)
  HybridBody1.AppendHybridShape HybridShapePointCoord2
  UpdateObjectErr wPart, HybridShapePointCoord2, wPart.name & "/" & HybridBody1.name & "/" & HybridShapePointCoord2.name
  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  UpdateObjectErr wPart, absPlane, wPart.name & "/" & HybridBody1.name & "/" & absPlane.name
  Set absRef = wPart.CreateReferenceFromGeometry(absPlane)

  Set datpoint1 = hypFact.AddNewPointDatum(Reference0)
  HybridBody1.AppendHybridShape datpoint1
  Set datpoint2 = hypFact.AddNewPointDatum(Reference1)
  HybridBody1.AppendHybridShape datpoint2
  Set datpoint3 = hypFact.AddNewPointDatum(Reference2)
  HybridBody1.AppendHybridShape datpoint3
  Set datplane1 = hypFact.AddNewPlaneDatum(absRef)
  HybridBody1.AppendHybridShape datplane1

  hypFact.DeleteObjectForDatum Reference0
  hypFact.DeleteObjectForDatum Reference1
  hypFact.DeleteObjectForDatum Reference2
  hypFact.DeleteObjectForDatum absRef

  Set absdatRef = wPart.CreateReferenceFromGeometry(datplane1)

  UpdatePartErr wPart, wPart.name & "/" & HybridBody1.name
  wPart.InWorkObject = backWork
  Set toolCall2=absdatRef
End Function

Function toolCall3(wpart,body,absref)
  UpdateObjectErr wPart, Body, wPart.name & "/" & Body.name
  Set sketch = Body.Sketches.Add(absRef)
  CATIA.ActiveDocument.Selection.Clear
  CATIA.ActiveDocument.Selection.Add(sketch)
  CATIA.ActiveDocument.Selection.VisProperties.SetShow(1)
  CATIA.ActiveDocument.Selection.Clear

  Set factory2d = sketch.OpenEdition
  Set Axis2D7 = Sketch.AbsoluteAxis
  Set Line2D8 = Axis2D7.HorizontalReference
  Line2D8.ReportName = 1
  Set Line2D9 = Axis2D7.VerticalReference
  Line2D9.ReportName = 2
  Set constraints1 = Sketch.Constraints

  Set pk = Factory2D.CreatePoint(0, 0)
  Set cir = Factory2D.CreateClosedCircle(0, 0, 128)
  Set ref1 = wpart.CreateReferenceFromObject(pk)
  Set ref2 = wpart.CreateReferenceFromObject(cir)
  Set constraint1 = constraints1.AddMonoEltCst(catCstTypeReference, ref1)
  Set constraint1 = constraints1.AddMonoEltCst(catCstTypeReference, ref2)

  Set startPoint = Factory2D.CreatePoint(-31.7954844427801, -2.5893162338804)
  Set endPoint = Factory2D.CreatePoint(-31.879855351464, -2.77034704860868)
  Set cir = Factory2D.CreateCircle(-31.6806062490794, -2.75303245363905, 0.200000000000003, 2.18265627171759, 3.22827413714723)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-31.879855351464, -2.77034704860868)
  Set endPoint = Factory2D.CreatePoint(-31.7591915719665, -3.91838623608396)
  Set cir = Factory2D.CreateCircle(1.1379341913198e-11, 1.35447209004269e-12, 32.0000000000115, 3.22827450896414, 3.26435030611631)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-31.7591915719665, -3.91838623608396)
  Set endPoint = Factory2D.CreatePoint(-31.6390259694441, -4.07791945582489)
  Set cir = Factory2D.CreateCircle(-31.5606966246417, -3.89389632210844, 0.199999999999987, 3.26435030611628, 4.30996837549591)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-31.6390259694441, -4.07791945582489)
  Set endPoint = Factory2D.CreatePoint(-29.6306504795168, -4.69303390034484)
  Set cir = Factory2D.CreateCircle(-27.7225602640888, 5.12323788326949, 9.99999999999975, 4.30996854229716, 4.52040273600931)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-29.6306504795168, -4.69303390034484)
  Set endPoint = Factory2D.CreatePoint(-29.2823914063757, -4.7228259915809)
  Set cir = Factory2D.CreateCircle(-29.3173765097444, -3.08138043805281, 1.64181834033331, 4.52040260030869, 4.73369934744774)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-27.8056821429054, -4.78339974255463)
  Set endPoint = Factory2D.CreatePoint(-29.2823914063757, -4.7228259915809)
  Set cir = Factory2D.CreateCircle(-29.034922731426, -16.7202740225132, 12.0000000000001, 1.46817961028746, 1.59142017837897)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-26.9288867662939, -5.575397521982)
  Set endPoint = Factory2D.CreatePoint(-27.8056821429054, -4.78339974255463)
  Set cir = Factory2D.CreateCircle(-27.9081190123409, -5.77813925005409, 1, 0.204156988574619, 1.46817945574904)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-26.9288867662939, -5.575397521982)
  Set endPoint = Factory2D.CreatePoint(-26.8684806566238, -5.85958592433223)
  Set cir = Factory2D.CreateCircle(1.13864473405556e-11, 2.40785169580704e-12, 27.5000000000116, 3.3457496421644, 3.35631468549382)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-27.3473386259892, -6.9397367373111)
  Set endPoint = Factory2D.CreatePoint(-26.8684806566238, -5.85958592433223)
  Set cir = Factory2D.CreateCircle(-27.8455163168647, -6.07266177612613, 0.999999999999989, 5.23388480973736, 0.214722031904035)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-28.6717420478327, -7.5957053500068)
  Set endPoint = Factory2D.CreatePoint(-27.3473386259892, -6.9397367373111)
  Set cir = Factory2D.CreateCircle(-33.3254699015225, 3.46516338006098, 12, 5.11064414928117, 5.23388471218978)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-28.6717420478327, -7.5957053500068)
  Set endPoint = Factory2D.CreatePoint(-28.9777750104108, -7.76457150833879)
  Set cir = Factory2D.CreateCircle(-28.0360664758879, -9.10947020291084, 1.64181834033335, 1.96836498019644, 2.18166172986684)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-28.9777750104108, -7.76457150833879)
  Set endPoint = Factory2D.CreatePoint(-30.5623277056265, -9.14338639257939)
  Set cir = Factory2D.CreateCircle(-23.2420104251614, -15.9560917959658, 10.0000000000003, 2.18166159206222, 2.39209578195694)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-30.5623277056265, -9.14338639257939)
  Set endPoint = Factory2D.CreatePoint(-30.6072164873759, -9.33800293932845)
  Set cir = Factory2D.CreateCircle(-30.4159213600172, -9.27964050064712, 0.200000000000015, 2.39209578195699, 3.43771360234321)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-30.6072164873759, -9.33800293932845)
  Set endPoint = Factory2D.CreatePoint(-30.2504987297431, -10.4358673143066)
  Set cir = Factory2D.CreateCircle(-1.86197723905934e-11, -5.98099347826064e-12, 31.9999999999804, 3.43771401892192, 3.47378981635564)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-30.2504987297431, -10.4358673143066)
  Set endPoint = Factory2D.CreatePoint(-30.0997902124871, -10.5669305168349)
  Set cir = Factory2D.CreateCircle(-30.0614331126822, -10.3706431435922, 0.200000000000004, 3.47378981635564, 4.51940788573515)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-30.0997902124871, -10.5669305168349)
  Set endPoint = Factory2D.CreatePoint(-28.0074130614356, -10.7510384910111)
  Set cir = Factory2D.CreateCircle(-28.1819368592889, -0.752561534795445, 9.99999999999963, 4.51940805253648, 4.72984224624863)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-28.0074130614356, -10.7510384910111)
  Set endPoint = Factory2D.CreatePoint(-27.6605701605458, -10.7077724208348)
  Set cir = Factory2D.CreateCircle(-28.0360664758878, -9.10947020291122, 1.64181834033334, 4.72984211054801, 4.94313885768774)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-26.2035367141444, -10.4599973881779)
  Set endPoint = Factory2D.CreatePoint(-27.6605701605458, -10.7077724208348)
  Set cir = Factory2D.CreateCircle(-24.9240995642786, -22.3915957965877, 12.000000000001, 1.67761913457574, 1.80085968861819)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-25.1812356551063, -11.052392088684)
  Set endPoint = Factory2D.CreatePoint(-26.2035367141444, -10.4599973881779)
  Set cir = Factory2D.CreateCircle(-26.0969169516556, -11.4542972555453, 1, 0.413596498813947, 1.67761913457576)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-25.1812356551063, -11.052392088684)
  Set endPoint = Factory2D.CreatePoint(-25.0630634726194, -11.3178111562021)
  Set cir = Factory2D.CreateCircle(1.11288755988426e-10, 4.97362151463676e-11, 27.5000000001219, 3.55518915240375, 3.56575419573313)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-25.3068812509889, -12.4739182402329)
  Set endPoint = Factory2D.CreatePoint(-25.0630634726194, -11.3178111562021)
  Set cir = Factory2D.CreateCircle(-25.9744475988965, -11.7293679255185, 1.00000000000001, 5.44332433823317, 0.424161542143346)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-26.4659597506727, -13.3909113318456)
  Set endPoint = Factory2D.CreatePoint(-25.3068812509889, -12.4739182402329)
  Set cir = Factory2D.CreateCircle(-33.317676404809, -3.53931354816482, 11.9999999999997, 5.32008365952049, 5.44332422395047)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-26.4659597506727, -13.3909113318456)
  Set endPoint = Factory2D.CreatePoint(-26.7301959022576, -13.6197151815738)
  Set cir = Factory2D.CreateCircle(-25.5294458050621, -14.7394324078142, 1.64181834033323, 2.17780449043577, 2.39110123295652)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-26.7301959022576, -13.6197151815738)
  Set endPoint = Factory2D.CreatePoint(-27.9934505934176, -15.2978466910869)
  Set cir = Factory2D.CreateCircle(-19.4166587094591, -20.4396985928115, 10.0000000000002, 2.39110110112769, 2.60153529219627)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-27.9934505934176, -15.2978466910869)
  Set endPoint = Factory2D.CreatePoint(-27.9968953922899, -15.4975433018649)
  Set cir = Factory2D.CreateCircle(-27.8219147557384, -15.4006837291214, 0.199999999999997, 2.60153529219623, 3.64715311258254)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-27.9968953922899, -15.4975433018649)
  Set endPoint = Factory2D.CreatePoint(-27.419713935032, -16.4972509140467)
  Set cir = Factory2D.CreateCircle(7.28661575521983e-12, 4.29345448083041e-12, 32.0000000000085, 3.64715352916125, 3.68322932659494)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-27.419713935032, -16.4972509140467)
  Set endPoint = Factory2D.CreatePoint(-27.2450491779474, -16.5941160083285)
  Set cir = Factory2D.CreateCircle(-27.248340722938, -16.3941430958339, 0.199999999999994, 3.68322932659492, 4.7288474483759)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-27.2450491779474, -16.5941160083285)
  Set endPoint = Factory2D.CreatePoint(-25.1601172980909, -16.3391711104138)
  Set cir = Factory2D.CreateCircle(-27.4096275818015, -6.59547040259769, 10.0000000000008, 4.72884756382384, 4.93928175648793)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-25.1601172980909, -16.3391711104138)
  Set endPoint = Factory2D.CreatePoint(-24.8298492685594, -16.2247378137056)
  Set cir = Factory2D.CreateCircle(-25.529445805062, -14.7394324078142, 1.64181834033378, 4.93928162078736, 5.15257836792704)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-23.4561706645289, -15.6794429201376)
  Set endPoint = Factory2D.CreatePoint(-24.8298492685594, -16.2247378137056)
  Set cir = Factory2D.CreateCircle(-19.7239736470735, -27.0842973875521, 12.0000000000003, 1.8870586307661, 2.01029919885751)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-22.3330437128156, -16.0463440858492)
  Set endPoint = Factory2D.CreatePoint(-23.4561706645289, -15.6794429201376)
  Set cir = Factory2D.CreateCircle(-23.1451543932816, -16.6298475071528, 1.00000000000001, 0.623036009053258, 1.88705847622767)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-22.3330437128156, -16.0463440858492)
  Set endPoint = Factory2D.CreatePoint(-22.1622701489397, -16.2813937316625)
  Set cir = Factory2D.CreateCircle(1.8165025039707e-10, 1.32118316287233e-10, 27.5000000002246, 3.76462866264308, 3.77519370597243)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-22.1603917358849, -17.4629296558029)
  Set endPoint = Factory2D.CreatePoint(-22.1622701489397, -16.2813937316625)
  Set cir = Factory2D.CreateCircle(-22.9681708816284, -16.8734444128138, 1, 5.6527638643777, 0.633601052382663)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-23.1034880146629, -18.600870231782)
  Set endPoint = Factory2D.CreatePoint(-22.1603917358849, -17.4629296558029)
  Set cir = Factory2D.CreateCircle(-31.8537405732561, -10.3891054908248, 11.9999999999997, 5.52952316975742, 5.65276373551522)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-23.1034880146629, -18.600870231782)
  Set endPoint = Factory2D.CreatePoint(-23.3143789669825, -18.8796119366565)
  Set cir = Factory2D.CreateCircle(-21.9070658486827, -19.7252106888523, 1.64181834033303, 2.38724400069249, 2.60054073125388)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-23.3143789669825, -18.8796119366565)
  Set endPoint = Factory2D.CreatePoint(-24.201125362797, -20.7837176819811)
  Set cir = Factory2D.CreateCircle(-14.7427058366885, -24.0299924805954, 9.99999999999946, 2.60054060940636, 2.8109748024356)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-24.201125362797, -20.7837176819811)
  Set endPoint = Factory2D.CreatePoint(-24.1629756245515, -20.9797666566463)
  Set cir = Factory2D.CreateCircle(-24.0119569722748, -20.8486431779534, 0.200000000000003, 2.81097480243555, 3.85659262282185)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-24.1629756245515, -20.9797666566463)
  Set endPoint = Factory2D.CreatePoint(-23.3905560669745, -21.8376254862501)
  Set cir = Factory2D.CreateCircle(4.69313476969546e-12, 4.33075797445781e-12, 32.0000000000064, 3.85659303940057, 3.89266883683427)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-23.3905560669745, -21.8376254862501)
  Set endPoint = Factory2D.CreatePoint(-23.1995687683662, -21.896059000845)
  Set cir = Factory2D.CreateCircle(-23.244365091556, -21.7011403269611, 0.199999999999982, 3.89266883683422, 4.93828695861526)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-23.1995687683662, -21.896059000845)
  Set endPoint = Factory2D.CreatePoint(-21.2132036771819, -21.2132035482496)
  Set cir = Factory2D.CreateCircle(-25.4393860530034, -12.15012556523, 9.99999999999994, 4.93828707406315, 5.14872126672726)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-21.2132036771819, -21.2132035482496)
  Set endPoint = Factory2D.CreatePoint(-20.9139448167011, -21.0326043091874)
  Set cir = Factory2D.CreateCircle(-21.907065848682, -19.7252106888529, 1.6418183403332, 5.14872113102663, 5.36201787816638)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-19.6836577151286, -20.213621660748)
  Set endPoint = Factory2D.CreatePoint(-20.9139448167011, -21.0326043091874)
  Set cir = Factory2D.CreateCircle(-13.661815435365, -30.5932852178026, 11.9999999999998, 2.09649815505437, 2.21973870909684)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-18.5087905944413, -20.3389938475609)
  Set endPoint = Factory2D.CreatePoint(-19.6836577151286, -20.213621660748)
  Set cir = Factory2D.CreateCircle(-19.1818375251483, -21.0785936238358, 0.999999999999991, 0.832475519292581, 2.09649815505441)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-18.5087905944413, -20.3389938475609)
  Set endPoint = Factory2D.CreatePoint(-18.2928792733802, -20.5334012742541)
  Set cir = Factory2D.CreateCircle(1.01302077837317e-10, 1.12702736032588e-10, 27.5000000001515, 3.97406817288239, 3.98463321621176)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-18.0453867668713, -21.6887272383006)
  Set endPoint = Factory2D.CreatePoint(-18.2928792733802, -20.5334012742541)
  Set cir = Factory2D.CreateCircle(-18.9580748833213, -21.2800704114997, 1.00000000000001, 5.86220339795252, 0.843040562621976)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-18.7312829895532, -22.9978818456948)
  Set endPoint = Factory2D.CreatePoint(-18.0453867668713, -21.6887272383006)
  Set cir = Factory2D.CreateCircle(-28.9976434274459, -16.7848436710768, 11.9999999999995, 5.73896267999674, 5.86220324769917)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-18.7312829895532, -22.9978818456948)
  Set endPoint = Factory2D.CreatePoint(-18.8796118094192, -23.3143790700172)
  Set cir = Factory2D.CreateCircle(-17.3272419929501, -23.8489026107255, 1.6418183403336, 2.59668351093185, 2.80998024149316)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-18.8796118094192, -23.3143790700172)
  Set endPoint = Factory2D.CreatePoint(-19.3510948239383, -25.3612404788303)
  Set cir = Factory2D.CreateCircle(-9.42442597550176, -26.5700603882808, 10.0000000000002, 2.80998011964568, 3.02041431267491)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-19.3510948239383, -25.3612404788303)
  Set endPoint = Factory2D.CreatePoint(-19.2730178817497, -25.5450735315003)
  Set cir = Factory2D.CreateCircle(-19.1525614469696, -25.3854168770193, 0.200000000000013, 3.02041431267493, 4.06603209203189)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-19.2730178817497, -25.5450735315003)
  Set endPoint = Factory2D.CreatePoint(-18.3391186584495, -26.2235910361512)
  Set cir = Factory2D.CreateCircle(-5.04840613757551e-12, -6.79634126754536e-12, 31.9999999999915, 4.06603254938345, 4.10210834707359)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-18.3391186584495, -26.2235910361512)
  Set endPoint = Factory2D.CreatePoint(-18.140155858362, -26.2410391361403)
  Set cir = Factory2D.CreateCircle(-18.2244991668341, -26.0596935921753, 0.200000000000011, 4.10210834707359, 5.1477265866585)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-18.140155858362, -26.2410391361403)
  Set endPoint = Factory2D.CreatePoint(-16.3391712633352, -25.1601171987826)
  Set cir = Factory2D.CreateCircle(-22.3573212819713, -17.1737619378898, 9.99999999999993, 5.14772658665855, 5.35816077696658)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-16.3391712633352, -25.1601171987826)
  Set endPoint = Factory2D.CreatePoint(-16.0840006201073, -24.9212450707201)
  Set cir = Factory2D.CreateCircle(-17.3272419929504, -23.8489026107252, 1.64181834033396, 5.358160641266, 5.57145738840948)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-15.0508743106819, -23.8643680866319)
  Set endPoint = Factory2D.CreatePoint(-16.0840006201073, -24.9212450707201)
  Set cir = Factory2D.CreateCircle(-7.00257033246819, -32.7651996811644, 11.9999999999983, 2.30593766529368, 2.42917821933564)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-13.8756145120588, -23.7427319808135)
  Set endPoint = Factory2D.CreatePoint(-15.0508743106819, -23.8643680866319)
  Set cir = Factory2D.CreateCircle(-14.3801823124973, -24.606104052843, 0.99999999999999, 1.0419150295319, 2.30593766529373)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-13.8756145120588, -23.7427319808135)
  Set endPoint = Factory2D.CreatePoint(-13.6240017946003, -23.8880006509697)
  Set cir = Factory2D.CreateCircle(-8.54125659088822e-11, -1.47394985106075e-10, 27.4999999998296, 4.18350768312165, 4.19407272645115)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-13.1417118159248, -24.9666233731505)
  Set endPoint = Factory2D.CreatePoint(-13.6240017946003, -23.8880006509697)
  Set cir = Factory2D.CreateCircle(-14.1194200416767, -24.7566552200959, 1, 6.07164292059199, 1.05248007286131)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-13.5404310151226, -26.3897756668428)
  Set endPoint = Factory2D.CreatePoint(-13.1417118159248, -24.9666233731505)
  Set cir = Factory2D.CreateCircle(-24.8742101177263, -22.4470036402862, 12.0000000000006, 5.94840219023846, 6.07164275897183)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-13.5404310151226, -26.3897756668428)
  Set endPoint = Factory2D.CreatePoint(-13.6197150213556, -26.7301959632151)
  Set cir = Factory2D.CreateCircle(-11.9901345167945, -26.9302830487779, 1.64181834033329, 2.80612302115376, 3.01941975173257)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-13.6197150213556, -26.7301959632151)
  Set endPoint = Factory2D.CreatePoint(-13.6553285844182, -28.8303553700207)
  Set cir = Factory2D.CreateCircle(-3.69425347577338, -27.9488891597025, 9.99999999999981, 3.019419629885, 3.22985382291423)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-13.6553285844182, -28.8303553700207)
  Set endPoint = Factory2D.CreatePoint(-13.540736769935, -28.9939381203611)
  Set cir = Factory2D.CreateCircle(-13.4561070822453, -28.8127260458144, 0.199999999999998, 3.2298538229142, 4.27547160227122)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-13.540736769935, -28.9939381203611)
  Set endPoint = Factory2D.CreatePoint(-12.4861737636953, -29.4634598230216)
  Set cir = Factory2D.CreateCircle(7.45536965496285e-12, 1.68220992691204e-11, 32.0000000000184, 4.27547205962278, 4.3115478573129)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-12.4861737636953, -29.4634598230216)
  Set endPoint = Factory2D.CreatePoint(-12.2879311141841, -29.4391599479872)
  Set cir = Factory2D.CreateCircle(-12.4081351776722, -29.2793131991277, 0.200000000000016, 4.31154785731294, 5.3571660968978)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-12.2879311141841, -29.4391599479872)
  Set endPoint = Factory2D.CreatePoint(-10.7510386612382, -28.0074129960915)
  Set cir = Factory2D.CreateCircle(-18.2981342885871, -21.4468225050106, 10.0000000000005, 5.35716609689788, 5.5676002872059)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-10.7510386612382, -28.0074129960915)
  Set endPoint = Factory2D.CreatePoint(-10.5511084168248, -27.7207078372699)
  Set cir = Factory2D.CreateCircle(-11.9901345167941, -26.9302830487781, 1.64181834033346, 5.56760015150528, 5.780896898645)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-9.76029537794445, -26.4721269765887)
  Set endPoint = Factory2D.CreatePoint(-10.5511084168248, -27.7207078372699)
  Set cir = Factory2D.CreateCircle(-0.0372793039803785, -33.5051176935892, 11.9999999999991, 2.51537716148405, 2.63861772957548)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-8.63600749291372, -26.1087987962361)
  Set endPoint = Factory2D.CreatePoint(-9.76029537794445, -26.4721269765887)
  Set cir = Factory2D.CreateCircle(-8.95004412901966, -27.0582096615538, 1, 1.25135453977122, 2.51537700694565)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-8.63600749291372, -26.1087987962361)
  Set endPoint = Factory2D.CreatePoint(-8.35969006218247, -26.1985797718931)
  Set cir = Factory2D.CreateCircle(-9.47686373820034e-11, -2.91418444930969e-10, 27.4999999996936, 4.39294719336094, 4.40351223669049)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-7.66368100273568, -27.1533582631768)
  Set endPoint = Factory2D.CreatePoint(-8.35969006218247, -26.1985797718931)
  Set cir = Factory2D.CreateCircle(-8.66367879171639, -27.151255399962, 0.999999999999999, 6.28108244241487, 1.26191958310063)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-7.7577972311491, -28.628309659181)
  Set endPoint = Factory2D.CreatePoint(-7.66368100273568, -27.1533582631768)
  Set cir = Factory2D.CreateCircle(-19.663654466159, -27.1281218377416, 12.0000000000014, 6.15784170047778, 6.28108227017645)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-7.7577972311491, -28.628309659181)
  Set endPoint = Factory2D.CreatePoint(-7.76457133221506, -28.9777750271094)
  Set cir = Factory2D.CreateCircle(-6.12900062720568, -28.8346808917636, 1.64181834033344, 3.01556253139307, 3.22885926197186)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-7.76457133221506, -28.9777750271094)
  Set endPoint = Factory2D.CreatePoint(-7.36275896022254, -31.0394453881472)
  Set cir = Factory2D.CreateCircle(2.19737562784192, -28.1062173611954, 10.0000000000001, 3.22885914012432, 3.43929333315355)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-7.36275896022254, -31.0394453881472)
  Set endPoint = Factory2D.CreatePoint(-7.21666049291414, -31.1756284833203)
  Set cir = Factory2D.CreateCircle(-7.17155626846126, -30.9807808276082, 0.199999999999991, 3.43929333315349, 4.4849110750252)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-7.21666049291414, -31.1756284833203)
  Set endPoint = Factory2D.CreatePoint(-6.08752316015837, -31.4156340342597)
  Set cir = Factory2D.CreateCircle(-1.01785246897634e-12, -4.19220214098459e-12, 31.9999999999957, 4.48491156962781, 4.52098736755223)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-6.08752316015837, -31.4156340342597)
  Set endPoint = Factory2D.CreatePoint(-5.89866481628098, -31.3506482053446)
  Set cir = Factory2D.CreateCircle(-6.04947614040738, -31.2192863215455, 0.200000000000013, 4.52098736755224, 5.56660560713711)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-5.89866481628098, -31.3506482053446)
  Set endPoint = Factory2D.CreatePoint(-4.69303408043786, -29.6306504509929)
  Set cir = Factory2D.CreateCircle(-13.4392310226007, -24.7825540153909, 9.99999999999971, 5.56660560713719, 5.77703979744522)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-4.69303408043786, -29.6306504509929)
  Set endPoint = Factory2D.CreatePoint(-4.55708214588754, -29.3086426526119)
  Set cir = Factory2D.CreateCircle(-6.12900062720562, -28.8346808917636, 1.64181834033361, 5.77703966174462, 5.99033640888431)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-4.04314482714464, -27.9229270033801)
  Set endPoint = Factory2D.CreatePoint(-4.55708214588754, -29.3086426526119)
  Set cir = Factory2D.CreateCircle(6.92964100897768, -32.7807012874114, 12.0000000000001, 2.72481667172338, 2.8480572398148)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-3.0189655061666, -27.3337858203465)
  Set endPoint = Factory2D.CreatePoint(-4.04314482714464, -27.9229270033801)
  Set cir = Factory2D.CreateCircle(-3.1287460700272, -28.3277416683591, 0.999999999999995, 1.46079405001053, 2.72481651718498)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-3.0189655061666, -27.3337858203465)
  Set endPoint = Factory2D.CreatePoint(-2.73001975980378, -27.3641552420513)
  Set cir = Factory2D.CreateCircle(-6.83764156406141e-12, -6.71818156661175e-11, 27.4999999999325, 4.60238670360029, 4.61295174692975)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-1.85071055773768, -28.1533611121586)
  Set endPoint = Factory2D.CreatePoint(-2.73001975980378, -27.3641552420513)
  Set cir = Factory2D.CreateCircle(-2.82929320561484, -28.3592154326713, 1, 0.207336645474613, 1.47135909333994)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-1.63611048213074, -29.6156491455704)
  Set endPoint = Factory2D.CreatePoint(-1.85071055773768, -28.1533611121586)
  Set cir = Factory2D.CreateCircle(-13.5937027577369, -30.6236109357166, 12.0000000000013, 0.0840959035351211, 0.207336473236175)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-1.63611048213074, -29.6156491455704)
  Set endPoint = Factory2D.CreatePoint(-1.57007861157732, -29.9588862902767)
  Set cir = Factory2D.CreateCircle(-8.10462807976364e-14, -29.4788648156289, 1.64181834033347, 3.22500204164981, 3.43829878415307)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-1.57007861157732, -29.9588862902767)
  Set endPoint = Factory2D.CreatePoint(-0.748401439027817, -31.8919626990277)
  Set cir = Factory2D.CreateCircle(7.99296887234238, -27.0351689954097, 10.0000000000004, 3.43829865232429, 3.64873284339286)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-0.748401439027817, -31.8919626990277)
  Set endPoint = Factory2D.CreatePoint(-0.577181516180982, -31.9947942874678)
  Set cir = Factory2D.CreateCircle(-0.573574032800416, -31.7948268249553, 0.200000000000002, 3.64873284339285, 4.69435058526449)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-0.577181516180982, -31.9947942874678)
  Set endPoint = Factory2D.CreatePoint(0.57718141665449, -31.9947942892632)
  Set cir = Factory2D.CreateCircle(-1.4033219031262e-13, 1.07078790279047e-11, 32.0000000000107, 4.69435107986714, 4.73042687779154)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(0.57718141665449, -31.9947942892632)
  Set endPoint = Factory2D.CreatePoint(0.748401439027798, -31.8919626990277)
  Set cir = Factory2D.CreateCircle(0.573574032800412, -31.7948268249553, 0.19999999999999, 4.73042687779148, 5.77604511737648)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(0.748401439027798, -31.8919626990277)
  Set endPoint = Factory2D.CreatePoint(1.57007860935365, -29.9588862975499)
  Set cir = Factory2D.CreateCircle(-7.99296887234234, -27.0351689954098, 10.0000000000003, 5.77604511737652, 5.98647930768454)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(1.57007860935365, -29.9588862975499)
  Set endPoint = Factory2D.CreatePoint(1.63611048213128, -29.6156491455637)
  Set cir = Factory2D.CreateCircle(-9.43689570931383e-14, -29.4788648156289, 1.64181834033363, 5.98647917198393, 6.19977591912363)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(1.8507105537628, -28.1533611310542)
  Set endPoint = Factory2D.CreatePoint(1.63611048213128, -29.6156491455637)
  Set cir = Factory2D.CreateCircle(13.5937027577358, -30.6236109357165, 12.0000000000002, 2.9342561819627, 3.05749675005412)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(2.73001975980375, -27.3641552420513)
  Set endPoint = Factory2D.CreatePoint(1.8507105537628, -28.1533611310542)
  Set cir = Factory2D.CreateCircle(2.82929320561482, -28.3592154326713, 1.00000000000001, 1.67023356024986, 2.93425602742429)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(2.73001975980375, -27.3641552420513)
  Set endPoint = Factory2D.CreatePoint(3.01896550616658, -27.3337858203465)
  Set cir = Factory2D.CreateCircle(-1.95683469428332e-11, 1.87352355851544e-10, 27.5000000001884, 4.81182621383967, 4.82239125716902)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(4.04314482401721, -27.9229269963159)
  Set endPoint = Factory2D.CreatePoint(3.01896550616658, -27.3337858203465)
  Set cir = Factory2D.CreateCircle(3.12874607002718, -28.3277416683591, 0.999999999999995, 0.416776144130345, 1.68079860357926)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(4.55708214588117, -29.3086426525909)
  Set endPoint = Factory2D.CreatePoint(4.04314482401721, -27.9229269963159)
  Set cir = Factory2D.CreateCircle(-6.92964100897705, -32.7807012874112, 11.9999999999994, 0.293535413776822, 0.416775982510209)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(4.55708214588117, -29.3086426525909)
  Set endPoint = Factory2D.CreatePoint(4.69303408244153, -29.6306504546076)
  Set cir = Factory2D.CreateCircle(6.12900062720541, -28.8346808917636, 1.64181834033344, 3.43444155187172, 3.64773830154212)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(4.69303408244153, -29.6306504546076)
  Set endPoint = Factory2D.CreatePoint(5.89866481628097, -31.3506482053447)
  Set cir = Factory2D.CreateCircle(13.4392310226013, -24.7825540153905, 10.0000000000005, 3.64773816373746, 3.85817235363218)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(5.89866481628097, -31.3506482053447)
  Set endPoint = Factory2D.CreatePoint(6.08752305555812, -31.4156340545285)
  Set cir = Factory2D.CreateCircle(6.04947614040738, -31.2192863215456, 0.200000000000005, 3.85817235363216, 4.90379006048752)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(6.08752305555812, -31.4156340545285)
  Set endPoint = Factory2D.CreatePoint(7.21666039593583, -31.1756285057692)
  Set cir = Factory2D.CreateCircle(-5.21804821573824e-12, 2.42827979946014e-11, 32.0000000000248, 4.90379058988761, 4.93986638803085)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(7.21666039593583, -31.1756285057692)
  Set endPoint = Factory2D.CreatePoint(7.36275895023749, -31.039445420691)
  Set cir = Factory2D.CreateCircle(7.17155626846122, -30.9807808276082, 0.200000000000015, 4.93986638803088, 5.98548445741033)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(7.36275895023749, -31.039445420691)
  Set endPoint = Factory2D.CreatePoint(7.76457132984335, -28.9777750542178)
  Set cir = Factory2D.CreateCircle(-2.19737562784172, -28.1062173611955, 9.99999999999986, 5.98548462421172, 6.19591881792386)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(7.76457132984335, -28.9777750542178)
  Set endPoint = Factory2D.CreatePoint(7.75779723115182, -28.6283096592028)
  Set cir = Factory2D.CreateCircle(6.12900062720558, -28.8346808917636, 1.64181834033351, 6.19591868222325, 0.126030122183378)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(7.66368100277627, -27.1533582824859)
  Set endPoint = Factory2D.CreatePoint(7.75779723115182, -28.6283096592028)
  Set cir = Factory2D.CreateCircle(19.663654466159, -27.1281218377417, 12.0000000000014, 3.14369569220202, 3.26693626029343)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(8.35969006218245, -26.1985797718931)
  Set endPoint = Factory2D.CreatePoint(7.66368100277627, -27.1533582824859)
  Set cir = Factory2D.CreateCircle(8.66367879171636, -27.151255399962, 0.999999999999991, 1.87967307048917, 3.14369553766361)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(8.35969006218245, -26.1985797718931)
  Set endPoint = Factory2D.CreatePoint(8.6360074929137, -26.1087987962361)
  Set cir = Factory2D.CreateCircle(-1.15107923193136e-11, 3.55946383479022e-11, 27.5000000000374, 5.02126572407896, 5.03183076740837)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(9.76029536662771, -26.4721269609435)
  Set endPoint = Factory2D.CreatePoint(8.6360074929137, -26.1087987962361)
  Set cir = Factory2D.CreateCircle(8.95004412901965, -27.0582096615537, 0.99999999999999, 0.626215665953238, 1.89023811381859)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(10.551108416828, -27.7207078372758)
  Set endPoint = Factory2D.CreatePoint(9.76029536662771, -26.4721269609435)
  Set cir = Factory2D.CreateCircle(0.0372793039797372, -33.5051176935895, 11.9999999999998, 0.502974924013754, 0.626215493714824)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(10.551108416828, -27.7207078372758)
  Set endPoint = Factory2D.CreatePoint(10.7510386639496, -28.0074129992107)
  Set cir = Factory2D.CreateCircle(11.9901345167942, -26.9302830487781, 1.64181834033354, 3.64388106212845, 3.85717781178137)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(10.7510386639496, -28.0074129992107)
  Set endPoint = Factory2D.CreatePoint(12.2879311141841, -29.4391599479873)
  Set cir = Factory2D.CreateCircle(18.2981342885871, -21.4468225050106, 10.0000000000006, 3.85717767397678, 4.0676118638715)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(12.2879311141841, -29.4391599479873)
  Set endPoint = Factory2D.CreatePoint(12.4861736655949, -29.4634598645951)
  Set cir = Factory2D.CreateCircle(12.4081351776722, -29.2793131991277, 0.200000000000012, 4.06761186387148, 5.11322957072681)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(12.4861736655949, -29.4634598645951)
  Set endPoint = Factory2D.CreatePoint(13.5407366865361, -28.99393815931)
  Set cir = Factory2D.CreateCircle(1.34381394900629e-11, -3.01447755646223e-11, 31.999999999967, 5.11323010012689, 5.1493058982702)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(13.5407366865361, -28.99393815931)
  Set endPoint = Factory2D.CreatePoint(13.6553285814176, -28.8303554039293)
  Set cir = Factory2D.CreateCircle(13.4561070822453, -28.8127260458144, 0.199999999999979, 5.14930589827011, 6.19492396764975)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(13.6553285814176, -28.8303554039293)
  Set endPoint = Factory2D.CreatePoint(13.6197150246719, -26.7301959902243)
  Set cir = Factory2D.CreateCircle(3.69425347577292, -27.9488891597025, 10.0000000000002, 6.19492413445104, 0.122173020983589)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(13.6197150246719, -26.7301959902243)
  Set endPoint = Factory2D.CreatePoint(13.5404310151298, -26.3897756668635)
  Set cir = Factory2D.CreateCircle(11.9901345167942, -26.9302830487781, 1.64181834033359, 0.122172885282991, 0.335469632422689)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(13.1417118175469, -24.9666233807039)
  Set endPoint = Factory2D.CreatePoint(13.5404310151298, -26.3897756668635)
  Set cir = Factory2D.CreateCircle(24.8742101177242, -22.4470036402868, 11.9999999999985, 3.35313520244133, 3.47637577053277)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(13.6240017946002, -23.8880006509697)
  Set endPoint = Factory2D.CreatePoint(13.1417118175469, -24.9666233807039)
  Set cir = Factory2D.CreateCircle(14.1194200416766, -24.7566552200959, 0.999999999999999, 2.0891125807285, 3.35313504790293)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(13.6240017946002, -23.8880006509697)
  Set endPoint = Factory2D.CreatePoint(13.8756145120588, -23.7427319808135)
  Set cir = Factory2D.CreateCircle(1.61751501082108e-10, -2.79914758039013e-10, 27.4999999996767, 5.23070523431821, 5.24127027764776)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(15.0508741713123, -23.8643679606113)
  Set endPoint = Factory2D.CreatePoint(13.8756145120588, -23.7427319808135)
  Set cir = Factory2D.CreateCircle(14.3801823124973, -24.606104052843, 0.999999999999994, 0.835655176192554, 2.0996776240579)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(16.084000620097, -24.9212450707082)
  Set endPoint = Factory2D.CreatePoint(15.0508741713123, -23.8643679606113)
  Set cir = Factory2D.CreateCircle(7.00257033246689, -32.7651996811657, 12.0000000000001, 0.712414434255469, 0.835655003954147)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(16.084000620097, -24.9212450707082)
  Set endPoint = Factory2D.CreatePoint(16.3391712854688, -25.1601172154615)
  Set cir = Factory2D.CreateCircle(17.3272419929502, -23.8489026107253, 1.64181834033372, 3.85332057235038, 4.06661733638366)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(16.3391712854688, -25.1601172154615)
  Set endPoint = Factory2D.CreatePoint(18.140155858362, -26.2410391361403)
  Set cir = Factory2D.CreateCircle(22.3573212819714, -17.1737619378897, 10.0000000000001, 4.06661718657422, 4.27705137411082)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(18.140155858362, -26.2410391361403)
  Set endPoint = Factory2D.CreatePoint(18.3391185711364, -26.2235910972124)
  Set cir = Factory2D.CreateCircle(18.2244991668341, -26.0596935921753, 0.200000000000015, 4.27705137411081, 5.32266908096613)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(18.3391185711364, -26.2235910972124)
  Set endPoint = Factory2D.CreatePoint(19.2730178082712, -25.5450735869377)
  Set cir = Factory2D.CreateCircle(-2.16715534406831e-12, 2.68229882749438e-12, 32.0000000000034, 5.32266961036624, 5.35874540850951)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(19.2730178082712, -25.5450735869377)
  Set endPoint = Factory2D.CreatePoint(19.3510948289931, -25.3612405203399)
  Set cir = Factory2D.CreateCircle(19.1525614469695, -25.3854168770193, 0.200000000000021, 5.35874540850951, 0.121178131833317)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(19.3510948289931, -25.3612405203399)
  Set endPoint = Factory2D.CreatePoint(18.8796118182786, -23.3143790957467)
  Set cir = Factory2D.CreateCircle(9.42442597550214, -26.5700603882807, 9.99999999999979, 0.121178336733254, 0.331612531222915)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(18.8796118182786, -23.3143790957467)
  Set endPoint = Factory2D.CreatePoint(18.7312829895503, -22.99788184569)
  Set cir = Factory2D.CreateCircle(17.3272419929502, -23.8489026107255, 1.64181834033348, 0.331612395522308, 0.54490914266134)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(18.045386764961, -21.6887272340341)
  Set endPoint = Factory2D.CreatePoint(18.7312829895503, -22.99788184569)
  Set cir = Factory2D.CreateCircle(28.9976434274462, -16.7848436710766, 11.9999999999999, 3.56257471268066, 3.68581528077217)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(18.2928792733801, -20.5334012742541)
  Set endPoint = Factory2D.CreatePoint(18.045386764961, -21.6887272340341)
  Set cir = Factory2D.CreateCircle(18.9580748833212, -21.2800704114997, 0.999999999999996, 2.29855209096781, 3.56257455814225)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(18.2928792733801, -20.5334012742541)
  Set endPoint = Factory2D.CreatePoint(18.5087905944413, -20.3389938475609)
  Set cir = Factory2D.CreateCircle(2.01794136955868e-11, -2.26236807066016e-11, 27.4999999999697, 5.44014474455759, 5.45070978788703)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(19.6836575369979, -20.2136215574041)
  Set endPoint = Factory2D.CreatePoint(18.5087905944413, -20.3389938475609)
  Set cir = Factory2D.CreateCircle(19.1818375251483, -21.0785936238358, 0.999999999999998, 1.04509470447353, 2.30911713429722)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(20.9139448167064, -21.0326043091915)
  Set endPoint = Factory2D.CreatePoint(19.6836575369979, -20.2136215574041)
  Set cir = Factory2D.CreateCircle(13.6618154353642, -30.5932852178038, 12.0000000000012, 0.921853944492403, 1.04509451569693)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(20.9139448167064, -21.0326043091915)
  Set endPoint = Factory2D.CreatePoint(21.2132036918365, -21.2132035550832)
  Set cir = Factory2D.CreateCircle(21.907065848682, -19.7252106888529, 1.64181834033316, 4.06276008260707, 4.27605683959131)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(21.2132036918365, -21.2132035550832)
  Set endPoint = Factory2D.CreatePoint(23.199568745404, -21.8960589955678)
  Set cir = Factory2D.CreateCircle(25.4393860530034, -12.15012556523, 9.99999999999992, 4.27605669565907, 4.48649088435015)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(23.199568745404, -21.8960589955678)
  Set endPoint = Factory2D.CreatePoint(23.3905561441681, -21.8376254035672)
  Set cir = Factory2D.CreateCircle(23.244365091556, -21.7011403269611, 0.200000000000014, 4.48649088435014, 5.53210968951696)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(23.3905561441681, -21.8376254035672)
  Set endPoint = Factory2D.CreatePoint(24.1629755695847, -20.9797667199531)
  Set cir = Factory2D.CreateCircle(-9.13402686819609e-12, 8.25295387585356e-12, 32.0000000000123, 5.53210912747001, 5.56818491874881)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(24.1629755695847, -20.9797667199531)
  Set endPoint = Factory2D.CreatePoint(24.2011253738477, -20.7837177141786)
  Set cir = Factory2D.CreateCircle(24.0119569722748, -20.8486431779534, 0.200000000000006, 5.56818491874881, 0.330617680948701)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(24.2011253738477, -20.7837177141786)
  Set endPoint = Factory2D.CreatePoint(23.3143789809977, -18.8796119599818)
  Set cir = Factory2D.CreateCircle(14.7427058366876, -24.0299924805959, 10.0000000000004, 0.3306178477501, 0.541052041462227)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(23.3143789809977, -18.8796119599818)
  Set endPoint = Factory2D.CreatePoint(23.1034880146583, -18.6008702317771)
  Set cir = Factory2D.CreateCircle(21.9070658486823, -19.7252106888525, 1.64181834033337, 0.541051905761596, 0.754348652901325)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(22.1603918187531, -17.4629297693583)
  Set endPoint = Factory2D.CreatePoint(23.1034880146583, -18.6008702317771)
  Set cir = Factory2D.CreateCircle(31.8537405732558, -10.3891054908252, 11.9999999999993, 3.77201423696892, 3.8952547910114)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(22.1622701489397, -16.2813937316625)
  Set endPoint = Factory2D.CreatePoint(22.1603918187531, -17.4629297693583)
  Set cir = Factory2D.CreateCircle(22.9681708816284, -16.8734444128138, 1.00000000000001, 2.50799160120716, 3.77201423696897)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(22.1622701489397, -16.2813937316625)
  Set endPoint = Factory2D.CreatePoint(22.3330437128156, -16.0463440858492)
  Set cir = Factory2D.CreateCircle(-1.24845911386728e-10, 9.057288252734e-11, 27.5000000001542, 5.64958425479695, 5.66014929812632)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(23.4561706363402, -15.679442910913)
  Set endPoint = Factory2D.CreatePoint(22.3330437128156, -16.0463440858492)
  Set cir = Factory2D.CreateCircle(23.1451543932816, -16.6298475071528, 0.999999999999986, 1.25453420702175, 2.51855664453655)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(24.8298492685655, -16.2247378137084)
  Set endPoint = Factory2D.CreatePoint(23.4561706363402, -15.679442910913)
  Set cir = Factory2D.CreateCircle(19.7239736470732, -27.0842973875526, 12.0000000000008, 1.13129345473172, 1.25453402529532)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(24.8298492685655, -16.2247378137084)
  Set endPoint = Factory2D.CreatePoint(25.1601173366264, -16.3391711193104)
  Set cir = Factory2D.CreateCircle(25.5294458050619, -14.7394324078145, 1.64181834033349, 4.27219959284641, 4.48549636407063)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(25.1601173366264, -16.3391711193104)
  Set endPoint = Factory2D.CreatePoint(27.2450491543898, -16.5941160079408)
  Set cir = Factory2D.CreateCircle(27.4096275818013, -6.59547040259943, 9.99999999999904, 4.48549620823634, 4.69593039458948)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(27.2450491543898, -16.5941160079408)
  Set endPoint = Factory2D.CreatePoint(27.419713996519, -16.4972508118505)
  Set cir = Factory2D.CreateCircle(27.248340722938, -16.3941430958339, 0.199999999999984, 4.69593039458936, 5.74154923051177)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(27.419713996519, -16.4972508118505)
  Set endPoint = Factory2D.CreatePoint(27.9968953516865, -15.4975433752165)
  Set cir = Factory2D.CreateCircle(1.2484235867305e-11, -7.14095449438901e-12, 31.9999999999856, 5.74154863790153, 5.77762442898815)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(27.9968953516865, -15.4975433752165)
  Set endPoint = Factory2D.CreatePoint(27.993450610921, -15.2978467202833)
  Set cir = Factory2D.CreateCircle(27.8219147557384, -15.4006837291214, 0.199999999999984, 5.77762442898806, 0.540057191188084)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(27.993450610921, -15.2978467202833)
  Set endPoint = Factory2D.CreatePoint(26.7301959074446, -13.6197151871362)
  Set cir = Factory2D.CreateCircle(19.4166587094591, -20.4396985928116, 10.0000000000003, 0.540057357989418, 0.750491551701547)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(26.7301959074446, -13.6197151871362)
  Set endPoint = Factory2D.CreatePoint(26.4659597506917, -13.3909113318588)
  Set cir = Factory2D.CreateCircle(25.5294458050619, -14.7394324078144, 1.64181834033351, 0.75049141600094, 0.96378816313997)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(25.3068813438135, -12.4739183234598)
  Set endPoint = Factory2D.CreatePoint(26.4659597506917, -13.3909113318588)
  Set cir = Factory2D.CreateCircle(33.3176764048089, -3.53931354816499, 11.9999999999995, 3.98145374720824, 4.10469430125081)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(25.0630634726194, -11.3178111562021)
  Set endPoint = Factory2D.CreatePoint(25.3068813438135, -12.4739183234598)
  Set cir = Factory2D.CreateCircle(25.9744475988965, -11.7293679255185, 1.00000000000001, 2.71743111144648, 3.98145374720829)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(25.0630634726194, -11.3178111562021)
  Set endPoint = Factory2D.CreatePoint(25.1812356551062, -11.0523920886841)
  Set cir = Factory2D.CreateCircle(-2.61170640669661e-10, 1.16440190822686e-10, 27.500000000286, 5.85902376503628, 5.8695888083656)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(26.2035365170274, -10.4599973670409)
  Set endPoint = Factory2D.CreatePoint(25.1812356551062, -11.0523920886841)
  Set cir = Factory2D.CreateCircle(26.0969169516556, -11.4542972555453, 1.00000000000001, 1.46397371726108, 2.72799615477585)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(27.6605701605245, -10.7077724208299)
  Set endPoint = Factory2D.CreatePoint(26.2035365170274, -10.4599973670409)
  Set cir = Factory2D.CreateCircle(24.9240995642789, -22.3915957965857, 11.999999999999, 1.34073296497342, 1.46397353553465)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(27.6605701605245, -10.7077724208299)
  Set endPoint = Factory2D.CreatePoint(28.0074130891456, -10.7510384914948)
  Set cir = Factory2D.CreateCircle(28.0360664758877, -9.10947020291079, 1.64181834033381, 4.48163910306836, 4.69493586710164)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(28.0074130891456, -10.7510384914948)
  Set endPoint = Factory2D.CreatePoint(30.099790179078, -10.5669305233635)
  Set cir = Factory2D.CreateCircle(28.1819368592889, -0.752561534795621, 9.99999999999948, 4.69493571729218, 4.90536990482879)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(30.099790179078, -10.5669305233635)
  Set endPoint = Factory2D.CreatePoint(30.2504986889219, -10.4358674326352)
  Set cir = Factory2D.CreateCircle(30.0614331126822, -10.3706431435922, 0.199999999999991, 4.90536990482871, 5.95098751855379)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(30.2504986889219, -10.4358674326352)
  Set endPoint = Factory2D.CreatePoint(30.6072164629104, -9.33800301951913)
  Set cir = Factory2D.CreateCircle(-5.52802248421358e-12, 1.74260605945165e-12, 32.0000000000058, 5.95098814050213, 5.98706393922746)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(30.6072164629104, -9.33800301951913)
  Set endPoint = Factory2D.CreatePoint(30.5623277216778, -9.14338640982668)
  Set cir = Factory2D.CreateCircle(30.4159213600172, -9.27964050064712, 0.19999999999999, 5.98706393922737, 0.749496753828746)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(30.5623277216778, -9.14338640982668)
  Set endPoint = Factory2D.CreatePoint(28.9777750070253, -7.76457150596825)
  Set cir = Factory2D.CreateCircle(23.2420104251617, -15.9560917959654, 9.99999999999983, 0.749496869276761, 0.959931061940873)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(28.9777750070253, -7.76457150596825)
  Set endPoint = Factory2D.CreatePoint(28.6717420478571, -7.59570535001707)
  Set cir = Factory2D.CreateCircle(28.0360664758878, -9.1094702029111, 1.6418183403336, 0.959930926240275, 1.17322767337724)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(27.3473385720815, -6.93973670633851)
  Set endPoint = Factory2D.CreatePoint(28.6717420478571, -7.59570535001707)
  Set cir = Factory2D.CreateCircle(33.3254699015216, 3.46516338005898, 11.9999999999978, 4.19089324339861, 4.31413381149042)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(26.8684806566238, -5.85958592433225)
  Set endPoint = Factory2D.CreatePoint(27.3473385720815, -6.93973670633851)
  Set cir = Factory2D.CreateCircle(27.8455163168647, -6.07266177612614, 0.999999999999999, 2.92687062168577, 4.19089308886022)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(26.8684806566238, -5.85958592433225)
  Set endPoint = Factory2D.CreatePoint(26.9288867662939, -5.57539752198202)
  Set cir = Factory2D.CreateCircle(-9.37987465476908e-11, 1.94928517771586e-11, 27.5000000000958, 6.06846327527559, 6.07902831860498)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(27.8056821236979, -4.78339974453262)
  Set endPoint = Factory2D.CreatePoint(26.9288867662939, -5.57539752198202)
  Set cir = Factory2D.CreateCircle(27.9081190123409, -5.7781392500541, 0.999999999999988, 1.67341321714982, 2.93743566501518)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(29.2823914063813, -4.72282599158105)
  Set endPoint = Factory2D.CreatePoint(27.8056821236979, -4.78339974453262)
  Set cir = Factory2D.CreateCircle(29.0349227314259, -16.7202740225126, 11.9999999999995, 1.55017247521035, 1.67341304491143)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(29.2823914063813, -4.72282599158105)
  Set endPoint = Factory2D.CreatePoint(29.6306505067219, -4.69303389505673)
  Set cir = Factory2D.CreateCircle(29.3173765097444, -3.08138043805266, 1.64181834033349, 4.69107861332506, 4.90437537734092)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(29.6306505067219, -4.69303389505673)
  Set endPoint = Factory2D.CreatePoint(31.6390259381224, -4.07791946915698)
  Set cir = Factory2D.CreateCircle(27.7225602640886, 5.12323788326998, 10.0000000000003, 4.90437522753151, 5.1148094150681)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(31.6390259381224, -4.07791946915698)
  Set endPoint = Factory2D.CreatePoint(31.7591915566392, -3.91838636031401)
  Set cir = Factory2D.CreateCircle(31.5606966246418, -3.89389632210845, 0.199999999999994, 5.11480941506801, 6.1604270287931)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(31.7591915566392, -3.91838636031401)
  Set endPoint = Factory2D.CreatePoint(31.8798553449856, -2.77034712315882)
  Set cir = Factory2D.CreateCircle(-4.9880100050359e-12, 4.47197834319013e-13, 32.000000000005, 6.16042765074145, 6.19650344946678)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(31.8798553449856, -2.77034712315882)
  Set endPoint = Factory2D.CreatePoint(31.7954844427802, -2.58931623388043)
  Set cir = Factory2D.CreateCircle(31.6806062490794, -2.75303245363907, 0.200000000000009, 6.19650344946673, 0.958936381872009)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(31.7954844427802, -2.58931623388043)
  Set endPoint = Factory2D.CreatePoint(29.9588861978228, -1.5700787531607)
  Set cir = Factory2D.CreateCircle(26.0515747577444, -10.775127221813, 10.0000000000002, 0.958936381872164, 1.16937058197746)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(29.9588861978228, -1.5700787531607)
  Set endPoint = Factory2D.CreatePoint(29.6244316352455, -1.46853059613952)
  Set cir = Factory2D.CreateCircle(29.3173765097443, -3.08138043805269, 1.64181834033364, 1.16937049615286, 1.38266718361654)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(28.1925860031815, -1.10225540714214)
  Set endPoint = Factory2D.CreatePoint(29.6244316352455, -1.46853059613952)
  Set cir = Factory2D.CreateCircle(31.8767804501926, 10.3181960408788, 11.9999999999996, 4.40033275363793, 4.52357332172973)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(27.4996163066591, -0.145268670156258)
  Set endPoint = Factory2D.CreatePoint(28.1925860031815, -1.10225540714214)
  Set cir = Factory2D.CreateCircle(28.499602354174, -0.15055116725283, 1.00000000000001, 3.1363101319251, 4.40033259909953)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(27.4996163066591, -0.145268670156258)
  Set endPoint = Factory2D.CreatePoint(27.4996163066591, 0.145268670156221)
  Set cir = Factory2D.CreateCircle(-7.28093141333375e-11, -3.54730134155545e-13, 27.5000000000728, 6.2779027855149, 0.00528252166471326)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(28.192585984805, 1.10225540121389)
  Set endPoint = Factory2D.CreatePoint(27.4996163066591, 0.145268670156221)
  Set cir = Factory2D.CreateCircle(28.499602354174, 0.150551167252798, 0.999999999999997, 1.88285272738914, 3.14687517525449)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(29.6244316352477, 1.4685305961399)
  Set endPoint = Factory2D.CreatePoint(28.192585984805, 1.10225540121389)
  Set cir = Factory2D.CreateCircle(31.8767804501929, -10.3181960408802, 12.000000000001, 1.75961198544967, 1.88285255515073)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(29.6244316352477, 1.4685305961399)
  Set endPoint = Factory2D.CreatePoint(29.9588863244122, 1.57007880689471)
  Set cir = Factory2D.CreateCircle(29.3173765097443, 3.08138043805273, 1.64181834033372, 4.90051812356439, 5.11381489478858)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(29.9588863244122, 1.57007880689471)
  Set endPoint = Factory2D.CreatePoint(31.7954844427802, 2.5893162338804)
  Set cir = Factory2D.CreateCircle(26.0515747577448, 10.7751272218121, 9.99999999999932, 5.1138147389543, 5.32424892530743)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(31.7954844427802, 2.5893162338804)
  Set endPoint = Factory2D.CreatePoint(31.8798553563057, 2.77034699289254)
  Set cir = Factory2D.CreateCircle(31.6806062490795, 2.75303245363905, 0.19999999999999, 5.32424892530732, 0.0866812039269019)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(31.8798553563057, 2.77034699289254)
  Set endPoint = Factory2D.CreatePoint(31.7591915719665, 3.91838623608393)
  Set cir = Factory2D.CreateCircle(1.64526170465251e-11, 1.66000546641953e-12, 31.9999999999835, 0.0866818536266351, 0.122757652526526)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(31.7591915719665, 3.91838623608393)
  Set endPoint = Factory2D.CreatePoint(31.6390259381224, 4.07791946915695)
  Set cir = Factory2D.CreateCircle(31.5606966246417, 3.89389632210842, 0.200000000000001, 0.122757652526445, 1.16837589211136)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(31.6390259381224, 4.07791946915695)
  Set endPoint = Factory2D.CreatePoint(29.6306504795168, 4.69303390034483)
  Set cir = Factory2D.CreateCircle(27.7225602640888, -5.12323788326956, 9.99999999999982, 1.16837589211148, 1.37881008241951)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(29.6306504795168, 4.69303390034483)
  Set endPoint = Factory2D.CreatePoint(29.282391406379, 4.72282599158096)
  Set cir = Factory2D.CreateCircle(29.3173765097444, 3.08138043805286, 1.64181834033325, 1.37880994671889, 1.59210669385591)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(27.805682310606, 4.78339972528508)
  Set endPoint = Factory2D.CreatePoint(29.282391406379, 4.72282599158096)
  Set cir = Factory2D.CreateCircle(29.034922731426, 16.7202740225145, 12.0000000000014, 4.60977227792621, 4.73301283196904)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(26.9288867662939, 5.57539752198199)
  Set endPoint = Factory2D.CreatePoint(27.805682310606, 4.78339972528508)
  Set cir = Factory2D.CreateCircle(27.9081190123409, 5.77813925005409, 1, 3.34574964216443, 4.60977227792625)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(26.9288867662939, 5.57539752198199)
  Set endPoint = Factory2D.CreatePoint(26.8684806566238, 5.85958592433222)
  Set cir = Factory2D.CreateCircle(-2.65245603259245e-11, -5.63726842983669e-12, 27.5000000000271, 0.204156988574609, 0.214722031904029)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(27.3473385463644, 6.9397366915627)
  Set endPoint = Factory2D.CreatePoint(26.8684806566238, 5.85958592433222)
  Set cir = Factory2D.CreateCircle(27.8455163168647, 6.0726617761261, 1, 2.09229224797903, 3.35631468549381)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(28.6717420478591, 7.5957053500179)
  Set endPoint = Factory2D.CreatePoint(27.3473385463644, 6.9397366915627)
  Set cir = Factory2D.CreateCircle(33.3254699015223, -3.46516338006058, 11.9999999999995, 1.96905149568899, 2.09229206625261)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(28.6717420478591, 7.5957053500179)
  Set endPoint = Factory2D.CreatePoint(28.9777750481819, 7.7645715347864)
  Set cir = Factory2D.CreateCircle(28.0360664758879, 9.10947020291095, 1.64181834033347, 5.10995763380369, 5.32325441154133)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(28.9777750481819, 7.7645715347864)
  Set endPoint = Factory2D.CreatePoint(30.5623277056265, 9.14338639257939)
  Set cir = Factory2D.CreateCircle(23.2420104251615, 15.9560917959656, 10.0000000000001, 5.32325425026301, 5.53368843554674)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(30.5623277056265, 9.14338639257939)
  Set endPoint = Factory2D.CreatePoint(30.607216501067, 9.33800289445306)
  Set cir = Factory2D.CreateCircle(30.4159213600172, 9.27964050064713, 0.200000000000002, 5.53368843554667, 0.296120714166176)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(30.607216501067, 9.33800289445306)
  Set endPoint = Factory2D.CreatePoint(30.2504987297431, 10.4358673143066)
  Set cir = Factory2D.CreateCircle(-8.74322836352803e-12, -2.93631785552861e-12, 32.0000000000092, 0.29612136386597, 0.332197162765831)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(30.2504987297431, 10.4358673143066)
  Set endPoint = Factory2D.CreatePoint(30.099790179078, 10.5669305233635)
  Set cir = Factory2D.CreateCircle(30.0614331126822, 10.3706431435922, 0.200000000000001, 0.332197162765737, 1.37781540235065)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(30.099790179078, 10.5669305233635)
  Set endPoint = Factory2D.CreatePoint(28.0074129634778, 10.7510384893012)
  Set cir = Factory2D.CreateCircle(28.1819368592889, 0.752561534794836, 10.0000000000002, 1.3778154023508, 1.58824960245609)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(28.0074129634778, 10.7510384893012)
  Set endPoint = Factory2D.CreatePoint(27.6605701605502, 10.7077724208359)
  Set cir = Factory2D.CreateCircle(28.0360664758878, 9.10947020291073, 1.64181834033382, 1.5882495166315, 1.80154620409516)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(26.2035367141444, 10.4599973881779)
  Set endPoint = Factory2D.CreatePoint(27.6605701605502, 10.7077724208359)
  Set cir = Factory2D.CreateCircle(24.9240995642784, 22.3915957965889, 12.0000000000022, 4.81921178816553, 4.94245234220835)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(25.1812356551063, 11.052392088684)
  Set endPoint = Factory2D.CreatePoint(26.2035367141444, 10.4599973881779)
  Set cir = Factory2D.CreateCircle(26.0969169516556, 11.4542972555453, 1.00000000000001, 3.55518915240375, 4.81921178816556)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(25.1812356551063, 11.052392088684)
  Set endPoint = Factory2D.CreatePoint(25.0630634726194, 11.3178111562021)
  Set cir = Factory2D.CreateCircle(-1.1601386518123e-10, -5.21858112279006e-11, 27.5000000001272, 0.413596498813966, 0.424161542143347)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(25.3068811762878, 12.4739181732556)
  Set endPoint = Factory2D.CreatePoint(25.0630634726194, 11.3178111562021)
  Set cir = Factory2D.CreateCircle(25.9744475988965, 11.7293679255185, 1, 2.30173178497389, 3.56575419573313)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(26.465959750708, 13.3909113318702)
  Set endPoint = Factory2D.CreatePoint(25.3068811762878, 12.4739181732556)
  Set cir = Factory2D.CreateCircle(33.3176764048092, 3.53931354816451, 12.0000000000001, 2.17849100592712, 2.30173157872155)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(26.465959750708, 13.3909113318702)
  Set endPoint = Factory2D.CreatePoint(26.7301959417102, 13.6197152238815)
  Set cir = Factory2D.CreateCircle(25.5294458050619, 14.7394324078145, 1.64181834033363, 5.31939714405173, 5.53269392178063)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(26.7301959417102, 13.6197152238815)
  Set endPoint = Factory2D.CreatePoint(27.9934505934176, 15.2978466910869)
  Set cir = Factory2D.CreateCircle(19.4166587094591, 20.4396985928116, 10.0000000000003, 5.53269376050233, 5.74312794578606)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(27.9934505934176, 15.2978466910869)
  Set endPoint = Factory2D.CreatePoint(27.9968954176306, 15.4975432560859)
  Set cir = Factory2D.CreateCircle(27.8219147557385, 15.4006837291214, 0.199999999999987, 5.74312794578597, 0.505560197369695)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(27.9968954176306, 15.4975432560859)
  Set endPoint = Factory2D.CreatePoint(27.419713935032, 16.4972509140467)
  Set cir = Factory2D.CreateCircle(1.81756831807434e-11, 1.06137321154165e-11, 31.999999999979, 0.505560873936292, 0.541636673005162)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(27.419713935032, 16.4972509140467)
  Set endPoint = Factory2D.CreatePoint(27.2450491543898, 16.5941160079407)
  Set cir = Factory2D.CreateCircle(27.248340722938, 16.3941430958339, 0.200000000000017, 0.54163667300512, 1.58725491258994)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(27.2450491543898, 16.5941160079407)
  Set endPoint = Factory2D.CreatePoint(25.1601172980909, 16.3391711104138)
  Set cir = Factory2D.CreateCircle(27.4096275818014, 6.59547040259859, 9.99999999999985, 1.58725491259012, 1.79768910289815)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(25.1601172980909, 16.3391711104138)
  Set endPoint = Factory2D.CreatePoint(24.8298492685605, 16.224737813706)
  Set cir = Factory2D.CreateCircle(25.5294458050621, 14.7394324078139, 1.64181834033409, 1.79768896719759, 2.01098571433655)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(23.4561708247551, 15.6794429725711)
  Set endPoint = Factory2D.CreatePoint(24.8298492685605, 16.224737813706)
  Set cir = Factory2D.CreateCircle(19.7239736470736, 27.0842973875519, 12.0000000000001, 5.02865129840484, 5.1518918524474)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(22.3330437128156, 16.0463440858492)
  Set endPoint = Factory2D.CreatePoint(23.4561708247551, 15.6794429725711)
  Set cir = Factory2D.CreateCircle(23.1451543932816, 16.6298475071528, 0.999999999999997, 3.76462866264306, 5.02865129840489)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(22.3330437128156, 16.0463440858492)
  Set endPoint = Factory2D.CreatePoint(22.1622701489397, 16.2813937316625)
  Set cir = Factory2D.CreateCircle(-1.20714105378283e-10, -8.78550565630576e-11, 27.5000000001493, 0.623036009053276, 0.633601052382649)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(22.1603916861174, 17.4629295876059)
  Set endPoint = Factory2D.CreatePoint(22.1622701489397, 16.2813937316625)
  Set cir = Factory2D.CreateCircle(22.9681708816284, 16.8734444128138, 1.00000000000001, 2.51117129521322, 3.77519370597244)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(23.1034880146727, 18.6008702317924)
  Set endPoint = Factory2D.CreatePoint(22.1603916861174, 17.4629295876059)
  Set cir = Factory2D.CreateCircle(31.8537405732559, 10.389105490825, 11.9999999999994, 2.38793051616643, 2.51117108896088)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(23.1034880146727, 18.6008702317924)
  Set endPoint = Factory2D.CreatePoint(23.3143790068748, 18.8796120030484)
  Set cir = Factory2D.CreateCircle(21.9070658486824, 19.7252106888525, 1.64181834033342, 5.52883665429106, 5.74213343201999)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(23.3143790068748, 18.8796120030484)
  Set endPoint = Factory2D.CreatePoint(24.201125362797, 20.7837176819811)
  Set cir = Factory2D.CreateCircle(14.7427058366887, 24.0299924805954, 9.99999999999931, 5.74213327074164, 5.95256745602539)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(24.201125362797, 20.7837176819811)
  Set endPoint = Factory2D.CreatePoint(24.1629756588565, 20.9797666171364)
  Set cir = Factory2D.CreateCircle(24.0119569722748, 20.8486431779534, 0.200000000000019, 5.95256745602539, 0.714999707608935)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(24.1629756588565, 20.9797666171364)
  Set endPoint = Factory2D.CreatePoint(23.3905560669746, 21.8376254862501)
  Set cir = Factory2D.CreateCircle(2.75548472927767e-11, 2.47268872044515e-11, 31.999999999963, 0.715000384175608, 0.751076183244496)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(23.3905560669746, 21.8376254862501)
  Set endPoint = Factory2D.CreatePoint(23.199568745404, 21.8960589955678)
  Set cir = Factory2D.CreateCircle(23.244365091556, 21.7011403269611, 0.199999999999983, 0.751076183244304, 1.7966944228293)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(23.199568745404, 21.8960589955678)
  Set endPoint = Factory2D.CreatePoint(21.213203677182, 21.2132035482496)
  Set cir = Factory2D.CreateCircle(25.4393860530034, 12.1501255652302, 9.99999999999968, 1.79669442282944, 2.00712861313747)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(21.213203677182, 21.2132035482496)
  Set endPoint = Factory2D.CreatePoint(20.9139448167011, 21.0326043091874)
  Set cir = Factory2D.CreateCircle(21.9070658486823, 19.7252106888525, 1.64181834033363, 2.00712847743688, 2.22042522457657)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(19.6836577151286, 20.213621660748)
  Set endPoint = Factory2D.CreatePoint(20.9139448167011, 21.0326043091874)
  Set cir = Factory2D.CreateCircle(13.6618154353648, 30.593285217803, 12.0000000000003, 5.23809080864416, 5.36133136268663)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(18.5087905944414, 20.3389938475609)
  Set endPoint = Factory2D.CreatePoint(19.6836577151286, 20.213621660748)
  Set cir = Factory2D.CreateCircle(19.1818375251483, 21.0785936238358, 1, 3.97406817288238, 5.23809080864421)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(18.5087905944414, 20.3389938475609)
  Set endPoint = Factory2D.CreatePoint(18.2928792733802, 20.5334012742541)
  Set cir = Factory2D.CreateCircle(3.68061137123732e-12, 4.20641299569979e-12, 27.4999999999944, 0.832475519292558, 0.843040562621991)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(18.0453867458211, 21.6887271912872)
  Set endPoint = Factory2D.CreatePoint(18.2928792733802, 20.5334012742541)
  Set cir = Factory2D.CreateCircle(18.9580748833213, 21.2800704114997, 1, 2.72061079587352, 3.98463321621177)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(18.7312829895607, 22.9978818457071)
  Set endPoint = Factory2D.CreatePoint(18.0453867458211, 21.6887271912872)
  Set cir = Factory2D.CreateCircle(28.9976434274467, 16.7848436710764, 12.0000000000004, 2.59737002640576, 2.72061059840194)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(18.7312829895607, 22.9978818457071)
  Set endPoint = Factory2D.CreatePoint(18.8796118346361, 23.3143791432523)
  Set cir = Factory2D.CreateCircle(17.3272419929502, 23.8489026107255, 1.64181834033349, 5.73827616453036, 5.95157294225927)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(18.8796118346361, 23.3143791432523)
  Set endPoint = Factory2D.CreatePoint(19.3510948239383, 25.3612404788303)
  Set cir = Factory2D.CreateCircle(9.42442597550204, 26.5700603882807, 9.99999999999994, 5.95157278098097, 6.1620069662647)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(19.3510948239383, 25.3612404788303)
  Set endPoint = Factory2D.CreatePoint(19.2730179211205, 25.5450735017962)
  Set cir = Factory2D.CreateCircle(19.1525614469696, 25.3854168770193, 0.200000000000001, 6.16200696626463, 0.924439191845772)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(19.2730179211205, 25.5450735017962)
  Set endPoint = Factory2D.CreatePoint(18.3391186584495, 26.2235910361512)
  Set cir = Factory2D.CreateCircle(-1.1556977597138e-11, -1.59126045673474e-11, 32.0000000000197, 0.924439894252442, 0.960515693483781)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(18.3391186584495, 26.2235910361512)
  Set endPoint = Factory2D.CreatePoint(18.140155858362, 26.2410391361403)
  Set cir = Factory2D.CreateCircle(18.2244991668341, 26.0596935921753, 0.199999999999983, 0.960515693483632, 2.00613393306863)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(18.140155858362, 26.2410391361403)
  Set endPoint = Factory2D.CreatePoint(16.3391712633352, 25.1601171987826)
  Set cir = Factory2D.CreateCircle(22.3573212819715, 17.1737619378895, 10.0000000000003, 2.00613393306876, 2.21656812337678)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(16.3391712633352, 25.1601171987826)
  Set endPoint = Factory2D.CreatePoint(16.0840006201114, 24.9212450707249)
  Set cir = Factory2D.CreateCircle(17.3272419929505, 23.8489026107252, 1.64181834033398, 2.21656798767621, 2.42986473481586)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(15.050874310682, 23.8643680866319)
  Set endPoint = Factory2D.CreatePoint(16.0840006201114, 24.9212450707249)
  Set cir = Factory2D.CreateCircle(7.00257033246619, 32.7651996811663, 12.0000000000011, 5.44753031888349, 5.57077087292595)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(13.8756145120589, 23.7427319808134)
  Set endPoint = Factory2D.CreatePoint(15.050874310682, 23.8643680866319)
  Set cir = Factory2D.CreateCircle(14.3801823124973, 24.606104052843, 0.999999999999998, 4.1835076831217, 5.44753031888353)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(13.8756145120589, 23.7427319808134)
  Set endPoint = Factory2D.CreatePoint(13.6240017946003, 23.8880006509697)
  Set cir = Factory2D.CreateCircle(-1.6156853632765e-10, -2.78571832268426e-10, 27.500000000322, 1.04191502953192, 1.05248007286123)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(13.1417118077128, 24.9666233349117)
  Set endPoint = Factory2D.CreatePoint(13.6240017946003, 23.8880006509697)
  Set cir = Factory2D.CreateCircle(14.1194200416767, 24.7566552200959, 1.00000000000001, 2.93005030611284, 4.19407272645109)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(13.5404310151226, 26.3897756668428)
  Set endPoint = Factory2D.CreatePoint(13.1417118077128, 24.9666233349117)
  Set cir = Factory2D.CreateCircle(24.874210117726, 22.4470036402863, 12.0000000000003, 2.80680953664866, 2.93005010864126)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(13.5404310151226, 26.3897756668428)
  Set endPoint = Factory2D.CreatePoint(13.6197150320557, 26.7301960503601)
  Set cir = Factory2D.CreateCircle(11.9901345167946, 26.9302830487779, 1.64181834033321, 5.94771567474356, 6.16101245879932)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(13.6197150320557, 26.7301960503601)
  Set endPoint = Factory2D.CreatePoint(13.6553285844182, 28.8303553700207)
  Set cir = Factory2D.CreateCircle(3.69425347577332, 27.9488891597025, 9.99999999999988, 6.16101229225474, 0.0882611693244376)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(13.6553285844182, 28.8303553700207)
  Set endPoint = Factory2D.CreatePoint(13.5407368146213, 28.9939380994918)
  Set cir = Factory2D.CreateCircle(13.4561070822453, 28.8127260458144, 0.199999999999992, 0.0882611693243154, 1.13387870208513)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(13.5407368146213, 28.9939380994918)
  Set endPoint = Factory2D.CreatePoint(12.4861737636953, 29.4634598230216)
  Set cir = Factory2D.CreateCircle(2.38209452163574e-12, 5.31841237716435e-12, 31.9999999999942, 1.13387940449175, 1.16995520372312)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(12.4861737636953, 29.4634598230216)
  Set endPoint = Factory2D.CreatePoint(12.2879311330147, 29.4391599621478)
  Set cir = Factory2D.CreateCircle(12.4081351776722, 29.2793131991277, 0.199999999999996, 1.16995520372301, 2.21557332550389)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(12.2879311330147, 29.4391599621478)
  Set endPoint = Factory2D.CreatePoint(10.7510386612382, 28.0074129960915)
  Set cir = Factory2D.CreateCircle(18.2981342885867, 21.446822505011, 9.99999999999995, 2.215573440952, 2.42600763361611)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(10.7510386612382, 28.0074129960915)
  Set endPoint = Factory2D.CreatePoint(10.551108416827, 27.7207078372739)
  Set cir = Factory2D.CreateCircle(11.9901345167942, 26.9302830487781, 1.6418183403335, 2.42600749791549, 2.63930424505247)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(9.7602954767506, 26.4721271131869)
  Set endPoint = Factory2D.CreatePoint(10.551108416827, 27.7207078372739)
  Set cir = Factory2D.CreateCircle(0.0372793039783712, 33.5051176935905, 12.0000000000015, 5.65696982912281, 5.78021038316564)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(8.63600749291373, 26.1087987962361)
  Set endPoint = Factory2D.CreatePoint(9.7602954767506, 26.4721271131869)
  Set cir = Factory2D.CreateCircle(8.95004412901965, 27.0582096615538, 1.00000000000002, 4.39294719336104, 5.65696982912283)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(8.63600749291373, 26.1087987962361)
  Set endPoint = Factory2D.CreatePoint(8.35969006218249, 26.1985797718931)
  Set cir = Factory2D.CreateCircle(1.50025769585227e-10, 4.60744331576279e-10, 27.4999999995155, 1.25135453977112, 1.26191958310074)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(7.66368100265768, 27.1533582260708)
  Set endPoint = Factory2D.CreatePoint(8.35969006218249, 26.1985797718931)
  Set cir = Factory2D.CreateCircle(8.66367879171641, 27.151255399962, 1, 3.13948982593116, 4.40351223669041)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(7.75779723115272, 28.6283096592094)
  Set endPoint = Factory2D.CreatePoint(7.66368100265768, 27.1533582260708)
  Set cir = Factory2D.CreateCircle(19.6636544661576, 27.1281218377417, 12, 3.01624904688559, 3.13948961967883)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(7.75779723115272, 28.6283096592094)
  Set endPoint = Factory2D.CreatePoint(7.76457132456284, 28.9777751145747)
  Set cir = Factory2D.CreateCircle(6.12900062720586, 28.8346808917636, 1.64181834033328, 6.1571551850003, 0.0872666618590103)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(7.76457132456284, 28.9777751145747)
  Set endPoint = Factory2D.CreatePoint(7.36275896022255, 31.0394453881473)
  Set cir = Factory2D.CreateCircle(-2.19737562784217, 28.1062173611954, 10.0000000000004, 0.0872664953144754, 0.297700679563753)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(7.36275896022255, 31.0394453881473)
  Set endPoint = Factory2D.CreatePoint(7.21666053852246, 31.1756284727627)
  Set cir = Factory2D.CreateCircle(7.17155626846126, 30.9807808276082, 0.199999999999994, 0.297700679563658, 1.34331818736368)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(7.21666053852246, 31.1756284727627)
  Set endPoint = Factory2D.CreatePoint(6.0875231601584, 31.4156340342597)
  Set cir = Factory2D.CreateCircle(4.11137790479188e-12, 1.88009607882123e-11, 31.9999999999808, 1.34331891457506, 1.37939471396245)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(6.0875231601584, 31.4156340342597)
  Set endPoint = Factory2D.CreatePoint(5.89866481628101, 31.3506482053447)
  Set cir = Factory2D.CreateCircle(6.04947614040738, 31.2192863215456, 0.199999999999986, 1.3793947139623, 2.42501295354726)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(5.89866481628101, 31.3506482053447)
  Set endPoint = Factory2D.CreatePoint(4.69303408043788, 29.6306504509929)
  Set cir = Factory2D.CreateCircle(13.4392310226008, 24.7825540153909, 9.99999999999984, 2.4250129535474, 2.63544714385543)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(4.69303408043788, 29.6306504509929)
  Set endPoint = Factory2D.CreatePoint(4.55708214588886, 29.3086426526162)
  Set cir = Factory2D.CreateCircle(6.12900062720543, 28.8346808917637, 1.64181834033338, 2.63544700815481, 2.84874375529181)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(4.04314489539128, 27.9229271575362)
  Set endPoint = Factory2D.CreatePoint(4.55708214588886, 29.3086426526162)
  Set cir = Factory2D.CreateCircle(-6.92964100897897, 32.780701287412, 12.0000000000015, 5.86640933936213, 5.98964989340495)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(3.01896550616661, 27.3337858203465)
  Set endPoint = Factory2D.CreatePoint(4.04314489539128, 27.9229271575362)
  Set cir = Factory2D.CreateCircle(3.1287460700272, 28.3277416683591, 0.999999999999984, 4.60238670360033, 5.86640933936218)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(3.01896550616661, 27.3337858203465)
  Set endPoint = Factory2D.CreatePoint(2.73001975980377, 27.3641552420513)
  Set cir = Factory2D.CreateCircle(1.62119206947864e-11, 1.54358303916524e-10, 27.4999999998448, 1.46079405001049, 1.47135909333998)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(1.85071049339413, 28.1533614180328)
  Set endPoint = Factory2D.CreatePoint(2.73001975980377, 27.3641552420513)
  Set cir = Factory2D.CreateCircle(2.82929320561481, 28.3592154326713, 0.999999999999999, 3.34892898649587, 4.61295174692975)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(1.63611048213312, 29.6156491455418)
  Set endPoint = Factory2D.CreatePoint(1.85071049339413, 28.1533614180328)
  Set cir = Factory2D.CreateCircle(13.5937027577355, 30.6236109357164, 11.9999999999999, 3.2256885571273, 3.3489291007786)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(1.63611048213312, 29.6156491455418)
  Set endPoint = Factory2D.CreatePoint(1.57007864285873, 29.9588861879598)
  Set cir = Factory2D.CreateCircle(-1.62536650805123e-13, 29.4788648156288, 1.64181834033372, 0.0834093880426069, 0.296706065396552)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(1.57007864285873, 29.9588861879598)
  Set endPoint = Factory2D.CreatePoint(0.748401439027818, 31.8919626990277)
  Set cir = Factory2D.CreateCircle(-7.99296887234212, 27.0351689954098, 10.0000000000001, 0.296705988035302, 0.507140189803073)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(0.748401439027818, 31.8919626990277)
  Set endPoint = Factory2D.CreatePoint(0.577181416654512, 31.9947942892632)
  Set cir = Factory2D.CreateCircle(0.573574032800419, 31.7948268249553, 0.199999999999999, 0.507140189803044, 1.55275842938803)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(0.577181416654512, 31.9947942892632)
  Set endPoint = Factory2D.CreatePoint(-0.577181416654512, 31.9947942892632)
  Set cir = Factory2D.CreateCircle(9.78661596207075e-14, -8.31335000839317e-12, 32.0000000000083, 1.55275842938805, 1.58883422420175)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-0.577181416654512, 31.9947942892632)
  Set endPoint = Factory2D.CreatePoint(-0.74840142758482, 31.891962719623)
  Set cir = Factory2D.CreateCircle(-0.573574032800411, 31.7948268249553, 0.200000000000016, 1.5888342242018, 2.63445234598268)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-0.74840142758482, 31.891962719623)
  Set endPoint = Factory2D.CreatePoint(-1.57007863799812, 29.9588862038582)
  Set cir = Factory2D.CreateCircle(7.99296887234215, 27.0351689954098, 10.0000000000001, 2.63445246143064, 2.84488666389202)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-1.57007863799812, 29.9588862038582)
  Set endPoint = Factory2D.CreatePoint(-1.63611048213254, 29.6156491455488)
  Set cir = Factory2D.CreateCircle(-2.34257058195908e-13, 29.4788648156289, 1.64181834033332, 2.84488657806739, 3.05818326554299)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-1.85071051905839, 28.1533612960308)
  Set endPoint = Factory2D.CreatePoint(-1.63611048213254, 29.6156491455488)
  Set cir = Factory2D.CreateCircle(-13.5937027577363, 30.6236109357165, 12.0000000000007, 6.07584884960145, 6.19908940364266)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-2.73001975980377, 27.3641552420513)
  Set endPoint = Factory2D.CreatePoint(-1.85071051905839, 28.1533612960308)
  Set cir = Factory2D.CreateCircle(-2.82929320561483, 28.3592154326713, 1, 4.81182621383964, 6.07584884960145)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-2.73001975980377, 27.3641552420513)
  Set endPoint = Factory2D.CreatePoint(-3.01896550616659, 27.3337858203465)
  Set cir = Factory2D.CreateCircle(-3.57980312060135e-12, 3.6649794310506e-11, 27.4999999999632, 1.67023356024984, 1.68079860357929)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-4.04314485231269, 27.9229270602299)
  Set endPoint = Factory2D.CreatePoint(-3.01896550616659, 27.3337858203465)
  Set cir = Factory2D.CreateCircle(-3.12874607002719, 28.3277416683591, 1, 3.55836872782283, 4.82239125716906)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-4.55708214588119, 29.3086426525909)
  Set endPoint = Factory2D.CreatePoint(-4.04314485231269, 27.9229270602299)
  Set cir = Factory2D.CreateCircle(6.92964100897743, 32.7807012874113, 11.9999999999998, 3.43512806736662, 3.55836863027522)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-4.55708214588119, 29.3086426525909)
  Set endPoint = Factory2D.CreatePoint(-4.69303404428459, 29.6306503857707)
  Set cir = Factory2D.CreateCircle(-6.12900062720538, 28.8346808917636, 1.64181834033337, 0.2928488982819, 0.5061456000146)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-4.69303404428459, 29.6306503857707)
  Set endPoint = Factory2D.CreatePoint(-5.89866481628096, 31.3506482053446)
  Set cir = Factory2D.CreateCircle(-13.4392310226007, 24.7825540153909, 9.99999999999979, 0.506145502277158, 0.716579700042395)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-5.89866481628096, 31.3506482053446)
  Set endPoint = Factory2D.CreatePoint(-6.08752316015835, 31.4156340342597)
  Set cir = Factory2D.CreateCircle(-6.04947614040737, 31.2192863215455, 0.200000000000017, 0.71657970004243, 1.76219793962729)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-6.08752316015835, 31.4156340342597)
  Set endPoint = Factory2D.CreatePoint(-7.21666039593585, 31.1756285057692)
  Set cir = Factory2D.CreateCircle(-4.37339053860342e-12, 2.03890238026361e-11, 31.9999999999791, 1.76219793962735, 1.79827373444108)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-7.21666039593585, 31.1756285057692)
  Set endPoint = Factory2D.CreatePoint(-7.36275895023751, 31.0394454206909)
  Set cir = Factory2D.CreateCircle(-7.17155626846126, 30.9807808276082, 0.199999999999988, 1.79827373444106, 2.84389180382073)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-7.36275895023751, 31.0394454206909)
  Set endPoint = Factory2D.CreatePoint(-7.76457133838225, 28.9777749566179)
  Set cir = Factory2D.CreateCircle(2.19737562784142, 28.1062173611955, 9.99999999999957, 2.84389197062193, 3.05432617413134)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-7.76457133838225, 28.9777749566179)
  Set endPoint = Factory2D.CreatePoint(-7.75779723115009, 28.628309659189)
  Set cir = Factory2D.CreateCircle(-6.12900062720536, 28.8346808917636, 1.64181834033374, 3.05432608830674, 3.2676227757816)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-7.66368100313082, 27.1533584510729)
  Set endPoint = Factory2D.CreatePoint(-7.75779723115009, 28.628309659189)
  Set cir = Factory2D.CreateCircle(-19.6636544661578, 27.1281218377417, 12.0000000000001, 0.00210305266117851, 0.125343606702487)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-8.35969006218246, 26.1985797718931)
  Set endPoint = Factory2D.CreatePoint(-7.66368100313082, 27.1533584510729)
  Set cir = Factory2D.CreateCircle(-8.66367879171639, 27.151255399962, 1, 5.02126572407897, 0.00210305266119066)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-8.35969006218246, 26.1985797718931)
  Set endPoint = Factory2D.CreatePoint(-8.63600749291371, 26.1087987962361)
  Set cir = Factory2D.CreateCircle(-3.67528230071912e-12, 1.11093356736092e-11, 27.4999999999883, 1.87967307048916, 1.89023811381859)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-9.76029539436068, 26.4721269992839)
  Set endPoint = Factory2D.CreatePoint(-8.63600749291371, 26.1087987962361)
  Set cir = Factory2D.CreateCircle(-8.95004412901966, 27.0582096615538, 1.00000000000001, 3.76780827222385, 5.03183076740837)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-10.5511084168142, 27.7207078372507)
  Set endPoint = Factory2D.CreatePoint(-9.76029539436068, 26.4721269992839)
  Set cir = Factory2D.CreateCircle(-0.0372793039776358, 33.5051176935909, 12.0000000000023, 3.64456757760595, 3.76780814336134)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-10.5511084168142, 27.7207078372507)
  Set endPoint = Factory2D.CreatePoint(-10.7510386333252, 28.0074129639812)
  Set cir = Factory2D.CreateCircle(-11.9901345167942, 26.930283048778, 1.6418183403336, 0.502288408521234, 0.715585129760042)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-10.7510386333252, 28.0074129639812)
  Set endPoint = Factory2D.CreatePoint(-12.2879311141841, 29.4391599479872)
  Set cir = Factory2D.CreateCircle(-18.2981342885865, 21.4468225050113, 9.99999999999959, 0.715585015719029, 0.926019210281716)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-12.2879311141841, 29.4391599479872)
  Set endPoint = Factory2D.CreatePoint(-12.4861737636952, 29.4634598230216)
  Set cir = Factory2D.CreateCircle(-12.4081351776722, 29.2793131991277, 0.200000000000013, 0.926019210281746, 1.97163744986663)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-12.4861737636952, 29.4634598230216)
  Set endPoint = Factory2D.CreatePoint(-13.5407366865361, 28.99393815931)
  Set cir = Factory2D.CreateCircle(-8.71658301093703e-12, 1.99200655970344e-11, 31.9999999999783, 1.97163744986667, 2.00771324468041)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-13.5407366865361, 28.99393815931)
  Set endPoint = Factory2D.CreatePoint(-13.6553285823414, 28.8303553934898)
  Set cir = Factory2D.CreateCircle(-13.4561070822453, 28.8127260458143, 0.200000000000015, 2.00771324468045, 3.05333136646132)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-13.6553285823414, 28.8303553934898)
  Set endPoint = Factory2D.CreatePoint(-13.619715012732, 26.7301958929818)
  Set cir = Factory2D.CreateCircle(-3.69425347577327, 27.9488891597025, 9.99999999999991, 3.05333148190928, 3.26376568437066)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-13.619715012732, 26.7301958929818)
  Set endPoint = Factory2D.CreatePoint(-13.5404310151263, 26.3897756668536)
  Set cir = Factory2D.CreateCircle(-11.990134516794, 26.9302830487781, 1.64181834033377, 3.26376559854606, 3.47706228601887)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-13.1417118175469, 24.9666233807038)
  Set endPoint = Factory2D.CreatePoint(-13.5404310151263, 26.3897756668536)
  Set cir = Factory2D.CreateCircle(-24.8742101177252, 22.4470036402865, 11.9999999999995, 0.211542548851541, 0.334783116942086)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-13.6240017946003, 23.8880006509697)
  Set endPoint = Factory2D.CreatePoint(-13.1417118175469, 24.9666233807038)
  Set cir = Factory2D.CreateCircle(-14.1194200416767, 24.7566552200959, 1.00000000000001, 5.23070523431828, 0.2115423943131)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-13.6240017946003, 23.8880006509697)
  Set endPoint = Factory2D.CreatePoint(-13.8756149237467, 23.7427317402168)
  Set cir = Factory2D.CreateCircle(2.00746086420622e-11, -3.3800517940108e-11, 27.5000000000393, 2.08911258072851, 2.09967764139745)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-15.0508742425483, 23.8643680250242)
  Set endPoint = Factory2D.CreatePoint(-13.8756149237467, 23.7427317402168)
  Set cir = Factory2D.CreateCircle(-14.3801823124972, 24.606104052843, 1, 3.97724773374269, 5.2412698008105)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-16.084000620097, 24.9212450707082)
  Set endPoint = Factory2D.CreatePoint(-15.0508742425483, 23.8643680250242)
  Set cir = Factory2D.CreateCircle(-7.00257033246621, 32.7651996811663, 12.000000000001, 3.85400708784526, 3.97724764954063)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-16.084000620097, 24.9212450707082)
  Set endPoint = Factory2D.CreatePoint(-16.3391712416027, 25.160117182406)
  Set cir = Factory2D.CreateCircle(-17.3272419929499, 23.8489026107258, 1.64181834033315, 0.71172791876051, 0.925024649339336)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-16.3391712416027, 25.160117182406)
  Set endPoint = Factory2D.CreatePoint(-18.1401558583619, 26.2410391361403)
  Set cir = Factory2D.CreateCircle(-22.3573212819714, 17.1737619378896, 10.0000000000002, 0.925024527491805, 1.13545872052103)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-18.1401558583619, 26.2410391361403)
  Set endPoint = Factory2D.CreatePoint(-18.3391187011345, 26.2235910063)
  Set cir = Factory2D.CreateCircle(-18.2244991668341, 26.0596935921753, 0.199999999999991, 1.13545872052098, 2.18107722054348)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-18.3391187011345, 26.2235910063)
  Set endPoint = Factory2D.CreatePoint(-19.2730178082712, 25.5450735869376)
  Set cir = Factory2D.CreateCircle(1.84741111297626e-12, -2.58282284448796e-12, 32.0000000000032, 2.18107696173373, 2.21715275491971)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-19.2730178082712, 25.5450735869376)
  Set endPoint = Factory2D.CreatePoint(-19.3510948267864, 25.3612405022183)
  Set cir = Factory2D.CreateCircle(-19.1525614469695, 25.3854168770193, 0.20000000000001, 2.21715275491976, 3.26277087670068)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-19.3510948267864, 25.3612405022183)
  Set endPoint = Factory2D.CreatePoint(-18.8796117863818, 23.3143790031117)
  Set cir = Factory2D.CreateCircle(-9.42442597550148, 26.5700603882808, 10.0000000000005, 3.2627709921486, 3.47320519460997)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-18.8796117863818, 23.3143790031117)
  Set endPoint = Factory2D.CreatePoint(-18.7312829895481, 22.9978818456864)
  Set cir = Factory2D.CreateCircle(-17.3272419929504, 23.8489026107253, 1.64181834033319, 3.47320510878534, 3.68650179625373)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-18.0453868338554, 21.6887273879018)
  Set endPoint = Factory2D.CreatePoint(-18.7312829895481, 22.9978818456864)
  Set cir = Factory2D.CreateCircle(-28.9976434274451, 16.7848436710772, 11.9999999999987, 0.420982073139807, 0.544222627182026)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-18.2928792733802, 20.5334012742541)
  Set endPoint = Factory2D.CreatePoint(-18.0453868338554, 21.6887273879018)
  Set cir = Factory2D.CreateCircle(-18.9580748833213, 21.2800704114997, 1, 5.44014474455761, 0.420982073139839)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-18.2928792733802, 20.5334012742541)
  Set endPoint = Factory2D.CreatePoint(-18.5087902417727, 20.3389941684947)
  Set cir = Factory2D.CreateCircle(3.47881723428145e-11, -3.89412946333323e-11, 27.5000000000522, 2.2985520909678, 2.30911711695768)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-19.6836576072908, 20.213621598185)
  Set endPoint = Factory2D.CreatePoint(-18.5087902417727, 20.3389941684947)
  Set cir = Factory2D.CreateCircle(-19.1818375251482, 21.0785936238358, 0.999999999999985, 4.18668727679713, 5.45071026472415)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-20.9139448166836, 21.0326043091742)
  Set endPoint = Factory2D.CreatePoint(-19.6836576072908, 20.213621598185)
  Set cir = Factory2D.CreateCircle(-13.6618154353658, 30.5932852178014, 11.9999999999984, 4.06344659808457, 4.18668716251456)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-20.9139448166836, 21.0326043091742)
  Set endPoint = Factory2D.CreatePoint(-21.213203670289, 21.2132035450354)
  Set cir = Factory2D.CreateCircle(-21.9070658486824, 19.7252106888523, 1.64181834033384, 0.921167428999879, 1.13446417152055)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-21.213203670289, 21.2132035450354)
  Set endPoint = Factory2D.CreatePoint(-23.199568745404, 21.8960589955678)
  Set cir = Factory2D.CreateCircle(-25.4393860530035, 12.1501255652298, 10.0000000000002, 1.13446403969177, 1.34489823076035)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-23.199568745404, 21.8960589955678)
  Set endPoint = Factory2D.CreatePoint(-23.3905561025204, 21.8376254481765)
  Set cir = Factory2D.CreateCircle(-23.2443650915559, 21.7011403269611, 0.2, 1.34489823076033, 2.39051673078276)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-23.3905561025204, 21.8376254481765)
  Set endPoint = Factory2D.CreatePoint(-24.1629755695847, 20.9797667199531)
  Set cir = Factory2D.CreateCircle(-1.18340892640845e-11, 1.06865627458319e-11, 31.9999999999841, 2.39051647197305, 2.42659226515904)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-24.1629755695847, 20.9797667199531)
  Set endPoint = Factory2D.CreatePoint(-24.2011253704455, 20.7837177042659)
  Set cir = Factory2D.CreateCircle(-24.0119569722748, 20.8486431779534, 0.200000000000007, 2.42659226515906, 3.47221038693999)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-24.2011253704455, 20.7837177042659)
  Set endPoint = Factory2D.CreatePoint(-23.3143789305381, 18.8796118760028)
  Set cir = Factory2D.CreateCircle(-14.7427058366874, 24.0299924805959, 10.0000000000006, 3.47221050238792, 3.68264470484929)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-23.3143789305381, 18.8796118760028)
  Set endPoint = Factory2D.CreatePoint(-23.103488014654, 18.6008702317725)
  Set cir = Factory2D.CreateCircle(-21.9070658486823, 19.7252106888525, 1.64181834033347, 3.68264461902467, 3.89594130649493)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-22.1603918187531, 17.4629297693583)
  Set endPoint = Factory2D.CreatePoint(-23.103488014654, 18.6008702317725)
  Set cir = Factory2D.CreateCircle(-31.8537405732563, 10.3891054908247, 11.9999999999999, 0.630421583379133, 0.753662137421078)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-22.1622701489397, 16.2813937316625)
  Set endPoint = Factory2D.CreatePoint(-22.1603918187531, 17.4629297693583)
  Set cir = Factory2D.CreateCircle(-22.9681708816284, 16.8734444128138, 0.999999999999991, 5.64958425479692, 0.630421583379163)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-22.1622701489397, 16.2813937316625)
  Set endPoint = Factory2D.CreatePoint(-22.3330437128156, 16.0463440858492)
  Set cir = Factory2D.CreateCircle(4.91553464598837e-11, -3.59285934337095e-11, 27.5000000000609, 2.50799160120712, 2.51855664453653)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-23.4561706911498, 15.6794429288492)
  Set endPoint = Factory2D.CreatePoint(-22.3330437128156, 16.0463440858492)
  Set cir = Factory2D.CreateCircle(-23.1451543932816, 16.6298475071528, 1, 4.3961268029418, 5.66014929812634)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-24.8298492685396, 16.2247378136962)
  Set endPoint = Factory2D.CreatePoint(-23.4561706911498, 15.6794429288492)
  Set cir = Factory2D.CreateCircle(-19.7239736470734, 27.0842973875522, 12.0000000000004, 4.2728861083239, 4.39612667407931)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-24.8298492685396, 16.2247378136962)
  Set endPoint = Factory2D.CreatePoint(-25.1601172566349, 16.3391711008429)
  Set cir = Factory2D.CreateCircle(-25.5294458050619, 14.7394324078144, 1.64181834033358, 1.13060693923919, 1.343903660478)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-25.1601172566349, 16.3391711008429)
  Set endPoint = Factory2D.CreatePoint(-27.2450491543898, 16.5941160079408)
  Set cir = Factory2D.CreateCircle(-27.4096275818013, 6.59547040259895, 9.99999999999951, 1.34390354643699, 1.55433774099968)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-27.2450491543898, 16.5941160079408)
  Set endPoint = Factory2D.CreatePoint(-27.4197139682688, 16.4972508588044)
  Set cir = Factory2D.CreateCircle(-27.248340722938, 16.3941430958339, 0.199999999999995, 1.55433774099964, 2.59995630293525)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-27.4197139682688, 16.4972508588044)
  Set endPoint = Factory2D.CreatePoint(-27.9968953516865, 15.4975433752165)
  Set cir = Factory2D.CreateCircle(2.27373675443232e-12, -1.21858079182857e-12, 32.0000000000026, 2.59995598259933, 2.63603177539835)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-27.9968953516865, 15.4975433752165)
  Set endPoint = Factory2D.CreatePoint(-27.9934505934176, 15.2978466910869)
  Set cir = Factory2D.CreateCircle(-27.8219147557384, 15.4006837291214, 0.199999999999979, 2.6360317753983, 3.68165001498341)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-27.9934505934176, 15.2978466910869)
  Set endPoint = Factory2D.CreatePoint(-26.7301958406274, 13.6197151154834)
  Set cir = Factory2D.CreateCircle(-19.4166587094591, 20.4396985928115, 10.0000000000002, 3.68165001498332, 3.89208421508861)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-26.7301958406274, 13.6197151154834)
  Set endPoint = Factory2D.CreatePoint(-26.4659597506856, 13.3909113318546)
  Set cir = Factory2D.CreateCircle(-25.5294458050618, 14.7394324078144, 1.64181834033359, 3.89208412926399, 4.10538081673423)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-25.3068812182917, 12.4739182109165)
  Set endPoint = Factory2D.CreatePoint(-26.4659597506856, 13.3909113318546)
  Set cir = Factory2D.CreateCircle(-33.3176764048101, 3.5393135481634, 12.0000000000015, 0.839861079569511, 0.963101647660389)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-25.0630634726194, 11.3178111562021)
  Set endPoint = Factory2D.CreatePoint(-25.3068812182917, 12.4739182109165)
  Set cir = Factory2D.CreateCircle(-25.9744475988965, 11.7293679255185, 1, 5.85902376503624, 0.83986092503108)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-25.0630634726194, 11.3178111562021)
  Set endPoint = Factory2D.CreatePoint(-25.1812356551063, 11.052392088684)
  Set cir = Factory2D.CreateCircle(1.49963597095848e-10, -6.76152467349311e-11, 27.5000000001645, 2.71743111144644, 2.72799615477581)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-26.203536590183, 10.4599973748854)
  Set endPoint = Factory2D.CreatePoint(-25.1812356551063, 11.052392088684)
  Set cir = Factory2D.CreateCircle(-26.0969169516556, 11.4542972555453, 1.00000000000001, 4.60556629727591, 5.86958880836565)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-27.6605701605244, 10.7077724208298)
  Set endPoint = Factory2D.CreatePoint(-26.203536590183, 10.4599973748854)
  Set cir = Factory2D.CreateCircle(-24.9240995642788, 22.3915957965865, 11.9999999999998, 4.48232561856321, 4.60556618299319)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-27.6605701605244, 10.7077724208298)
  Set endPoint = Factory2D.CreatePoint(-28.0074130342277, 10.7510384905362)
  Set cir = Factory2D.CreateCircle(-28.0360664758878, 9.10947020291109, 1.64181834033349, 1.34004644947849, 1.55334318005728)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-28.0074130342277, 10.7510384905362)
  Set endPoint = Factory2D.CreatePoint(-30.099790179078, 10.5669305233635)
  Set cir = Factory2D.CreateCircle(-28.1819368592889, 0.752561534795383, 9.99999999999971, 1.55334305820976, 1.76377725123899)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-30.099790179078, 10.5669305233635)
  Set endPoint = Factory2D.CreatePoint(-30.250498708718, 10.435867375252)
  Set cir = Factory2D.CreateCircle(-30.0614331126822, 10.3706431435922, 0.200000000000006, 1.76377725123899, 2.80939516847327)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-30.250498708718, 10.435867375252)
  Set endPoint = Factory2D.CreatePoint(-30.6072164629104, 9.33800301951911)
  Set cir = Factory2D.CreateCircle(-2.90256707558001e-11, 9.49995637711254e-12, 31.9999999999695, 2.80939548880925, 2.84547128563769)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-30.6072164629104, 9.33800301951911)
  Set endPoint = Factory2D.CreatePoint(-30.5623277288177, 9.14338641749855)
  Set cir = Factory2D.CreateCircle(-30.4159213600172, 9.27964050064712, 0.200000000000002, 2.84547128563768, 3.89108935501722)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-30.5623277288177, 9.14338641749855)
  Set endPoint = Factory2D.CreatePoint(-28.9777749267708, 7.76457144977341)
  Set cir = Factory2D.CreateCircle(-23.2420104251619, 15.9560917959652, 9.99999999999958, 3.89108952181852, 4.10152372532794)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-28.9777749267708, 7.76457144977341)
  Set endPoint = Factory2D.CreatePoint(-28.67174204785, 7.5957053500141)
  Set cir = Factory2D.CreateCircle(-28.0360664758878, 9.10947020291096, 1.64181834033347, 4.10152363950332, 4.31482032697167)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-27.3473387182594, 6.93973679032496)
  Set endPoint = Factory2D.CreatePoint(-28.67174204785, 7.5957053500141)
  Set cir = Factory2D.CreateCircle(-33.3254699015219, -3.46516338005971, 11.9999999999986, 1.04930060385776, 1.17254115789998)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-26.8684806566238, 5.85958592433224)
  Set endPoint = Factory2D.CreatePoint(-27.3473387182594, 6.93973679032496)
  Set cir = Factory2D.CreateCircle(-27.8455163168647, 6.07266177612612, 0.999999999999993, 6.06846327527557, 1.0493006038578)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-26.8684806566238, 5.85958592433224)
  Set endPoint = Factory2D.CreatePoint(-26.9288867662939, 5.57539752198201)
  Set cir = Factory2D.CreateCircle(2.36152430943548e-10, -5.01731989288601e-11, 27.5000000002414, 2.92687062168581, 2.93743566501514)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-27.8056821707682, 4.78339973968537)
  Set endPoint = Factory2D.CreatePoint(-26.9288867662939, 5.57539752198201)
  Set cir = Factory2D.CreateCircle(-27.9081190123409, 5.77813925005409, 1.00000000000001, 4.81500582342043, 6.07902831860497)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-29.2823914063526, 4.72282599158043)
  Set endPoint = Factory2D.CreatePoint(-27.8056821707682, 4.78339973968537)
  Set cir = Factory2D.CreateCircle(-29.0349227314258, 16.7202740225111, 11.999999999998, 4.69176512880253, 4.81500569455796)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-29.2823914063526, 4.72282599158043)
  Set endPoint = Factory2D.CreatePoint(-29.630650472051, 4.69303390179605)
  Set cir = Factory2D.CreateCircle(-29.3173765097443, 3.08138043805252, 1.64181834033362, 1.54948595971783, 1.76278270223853)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-29.630650472051, 4.69303390179605)
  Set endPoint = Factory2D.CreatePoint(-31.6390259381224, 4.07791946915697)
  Set cir = Factory2D.CreateCircle(-27.7225602640886, -5.12323788326981, 10.0000000000001, 1.76278257040973, 1.97321676147831)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-31.6390259381224, 4.07791946915697)
  Set endPoint = Factory2D.CreatePoint(-31.7591915640722, 3.91838630006894)
  Set cir = Factory2D.CreateCircle(-31.5606966246417, 3.89389632210843, 0.200000000000009, 1.97321676147832, 3.01883467871256)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-31.7591915640722, 3.91838630006894)
  Set endPoint = Factory2D.CreatePoint(-31.8798553449856, 2.7703471231588)
  Set cir = Factory2D.CreateCircle(-1.00044417195022e-11, 1.16751053269581e-12, 31.9999999999899, 3.01883499904858, 3.054910795877)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-31.8798553449856, 2.7703471231588)
  Set endPoint = Factory2D.CreatePoint(-31.7954844620666, 2.58931624741352)
  Set cir = Factory2D.CreateCircle(-31.6806062490794, 2.75303245363905, 0.199999999999981, 3.05491079587694, 4.10052891765801)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-31.7954844620666, 2.58931624741352)
  Set endPoint = Factory2D.CreatePoint(-29.9588862880071, 1.57007879144166)
  Set cir = Factory2D.CreateCircle(-26.0515747577445, 10.7751272218128, 10.0000000000001, 4.10052903310588, 4.31096322576998)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-29.9588862880071, 1.57007879144166)
  Set endPoint = Factory2D.CreatePoint(-29.6244316352411, 1.46853059613867)
  Set cir = Factory2D.CreateCircle(-29.3173765097444, 3.08138043805254, 1.6418183403335, 4.31096309006938, 4.52425983720909)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-28.1925861636269, 1.10225545890119)
  Set endPoint = Factory2D.CreatePoint(-29.6244316352411, 1.46853059613867)
  Set cir = Factory2D.CreateCircle(-31.8767804501924, -10.3181960408783, 11.9999999999991, 1.25874011409709, 1.38198066813957)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-27.4996163066591, 0.145268670156244)
  Set endPoint = Factory2D.CreatePoint(-28.1925861636269, 1.10225545890119)
  Set cir = Factory2D.CreateCircle(-28.499602354174, 0.150551167252811, 1, 6.2779027855149, 1.25874011409712)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-27.4996163066591, 0.145268670156244)
  Set endPoint = Factory2D.CreatePoint(-27.4996163066591, -0.145268670156235)
  Set cir = Factory2D.CreateCircle(-1.817959116579e-10, -3.31859539848267e-13, 27.4999999998182, 3.13631013192503, 3.14687517525453)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-28.1925860449759, -1.10225542062484)
  Set endPoint = Factory2D.CreatePoint(-27.4996163066591, -0.145268670156235)
  Set cir = Factory2D.CreateCircle(-28.499602354174, -0.15055116725282, 1, 5.02444531775454, 0.00528252166471007)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-29.6244316352195, -1.46853059613454)
  Set endPoint = Factory2D.CreatePoint(-28.1925860449759, -1.10225542062484)
  Set cir = Factory2D.CreateCircle(-31.8767804501928, 10.31819604088, 12.0000000000008, 4.90120463904186, 5.02444520347183)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-29.6244316352195, -1.46853059613454)
  Set endPoint = Factory2D.CreatePoint(-29.9588862810062, -1.57007878846994)
  Set cir = Factory2D.CreateCircle(-29.3173765097444, -3.08138043805247, 1.64181834033344, 1.75892546995713, 1.97222221247786)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-29.9588862810062, -1.57007878846994)
  Set endPoint = Factory2D.CreatePoint(-31.7954844427801, -2.5893162338804)
  Set cir = Factory2D.CreateCircle(-26.0515747577446, -10.7751272218126, 9.99999999999986, 1.97222208064905, 2.18265627171763)
  cir.StartPoint = startPoint
  cir.EndPoint = endPoint
  Set ref1 = wpart.CreateReferenceFromObject(startPoint)
  Set ref2 = wpart.CreateReferenceFromObject(endPoint)
  Set ref3 = wpart.CreateReferenceFromObject(cir)
  Set constraint1 = constraints1.AddMonoEltCst(catCstTypeReference, ref1)
  Set constraint1 = constraints1.AddMonoEltCst(catCstTypeReference, ref2)
  Set constraint1 = constraints1.AddMonoEltCst(catCstTypeReference, ref3)

  Sketch.CloseEdition
  UpdateObjectErr wpart, Sketch, wPart.name & "/" & Body.name & "/" & Sketch.name
  Set sketch6 = sketch
  Set toolCall3=sketch6
End Function

Function toolCall4(wpart,HybridBody1)
  set backWork = wPart.InWorkObject 
  UpdateObjectErr wPart, HybridBody1, wPart.name & "/" & HybridBody1.name
  Set hypFact = wPart.HybridShapeFactory
  Set HybridShapePointCoord0 = hypFact.AddNewPointCoord(0, 0, 0)
  HybridBody1.AppendHybridShape HybridShapePointCoord0
  UpdateObjectErr wPart, HybridShapePointCoord0, wPart.name & "/" & HybridBody1.name & "/" & HybridShapePointCoord0.name
  Set HybridShapePointCoord1 = hypFact.AddNewPointCoord(0, 0, -1)
  HybridBody1.AppendHybridShape HybridShapePointCoord1
  UpdateObjectErr wPart, HybridShapePointCoord1, wPart.name & "/" & HybridBody1.name & "/" & HybridShapePointCoord1.name
  Set HybridShapePointCoord2 = hypFact.AddNewPointCoord(0, 1, 0)
  HybridBody1.AppendHybridShape HybridShapePointCoord2
  UpdateObjectErr wPart, HybridShapePointCoord2, wPart.name & "/" & HybridBody1.name & "/" & HybridShapePointCoord2.name
  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  UpdateObjectErr wPart, absPlane, wPart.name & "/" & HybridBody1.name & "/" & absPlane.name
  Set absRef = wPart.CreateReferenceFromGeometry(absPlane)

  Set datpoint1 = hypFact.AddNewPointDatum(Reference0)
  HybridBody1.AppendHybridShape datpoint1
  Set datpoint2 = hypFact.AddNewPointDatum(Reference1)
  HybridBody1.AppendHybridShape datpoint2
  Set datpoint3 = hypFact.AddNewPointDatum(Reference2)
  HybridBody1.AppendHybridShape datpoint3
  Set datplane1 = hypFact.AddNewPlaneDatum(absRef)
  HybridBody1.AppendHybridShape datplane1

  hypFact.DeleteObjectForDatum Reference0
  hypFact.DeleteObjectForDatum Reference1
  hypFact.DeleteObjectForDatum Reference2
  hypFact.DeleteObjectForDatum absRef

  Set absdatRef = wPart.CreateReferenceFromGeometry(datplane1)

  UpdatePartErr wPart, wPart.name & "/" & HybridBody1.name
  wPart.InWorkObject = backWork
  Set toolCall4=absdatRef
End Function

Function toolCall5(wpart,body,absref)
  UpdateObjectErr wPart, Body, wPart.name & "/" & Body.name
  Set sketch = Body.Sketches.Add(absRef)
  CATIA.ActiveDocument.Selection.Clear
  CATIA.ActiveDocument.Selection.Add(sketch)
  CATIA.ActiveDocument.Selection.VisProperties.SetShow(1)
  CATIA.ActiveDocument.Selection.Clear

  Set factory2d = sketch.OpenEdition
  Set Axis2D7 = Sketch.AbsoluteAxis
  Set Line2D8 = Axis2D7.HorizontalReference
  Line2D8.ReportName = 1
  Set Line2D9 = Axis2D7.VerticalReference
  Line2D9.ReportName = 2
  Set constraints1 = Sketch.Constraints

  Set startPoint = Factory2D.CreatePoint(-29, 0)
  Set endPoint = Factory2D.CreatePoint(-29, 6.49999999999994)
  Set line = factory2d.CreateLine(-29, 0, -29, 6.49999999999994)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-29, 6.49999999999994)
  Set endPoint = Factory2D.CreatePoint(0, 6.49999999999983)
  Set line = factory2d.CreateLine(-29, 6.49999999999994, 0, 6.49999999999983)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(0, 6.49999999999983)
  Set endPoint = Factory2D.CreatePoint(0, 5.6843418860808e-14)
  Set line = factory2d.CreateLine(0, 6.49999999999983, 0, 5.6843418860808e-14)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(0, 5.6843418860808e-14)
  Set endPoint = Factory2D.CreatePoint(-29, 0)
  Set line = factory2d.CreateLine(0, 5.6843418860808e-14, -29, 0)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set pk1 = Factory2D.CreatePoint(0, 5.6843418860808e-14)
  Set pk2 = Factory2D.CreatePoint(-29, 0)
  Set line = Factory2d.CreateLine(0, 5.6843418860808e-14, -29, 0)
  sketch.CenterLine = line
  Set ref1 = wpart.CreateReferenceFromObject(pk1)
  Set ref2 = wpart.CreateReferenceFromObject(pk2)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Sketch.CloseEdition
  UpdateObjectErr wpart, Sketch, wPart.name & "/" & Body.name & "/" & Sketch.name
  Set sketch8 = sketch
  Set toolCall5=sketch8
End Function

Function toolCall6(wpart,HybridBody1)
  set backWork = wPart.InWorkObject 
  UpdateObjectErr wPart, HybridBody1, wPart.name & "/" & HybridBody1.name
  Set hypFact = wPart.HybridShapeFactory
  Set HybridShapePointCoord0 = hypFact.AddNewPointCoord(0, 0, 0)
  HybridBody1.AppendHybridShape HybridShapePointCoord0
  UpdateObjectErr wPart, HybridShapePointCoord0, wPart.name & "/" & HybridBody1.name & "/" & HybridShapePointCoord0.name
  Set HybridShapePointCoord1 = hypFact.AddNewPointCoord(0, 0, -1)
  HybridBody1.AppendHybridShape HybridShapePointCoord1
  UpdateObjectErr wPart, HybridShapePointCoord1, wPart.name & "/" & HybridBody1.name & "/" & HybridShapePointCoord1.name
  Set HybridShapePointCoord2 = hypFact.AddNewPointCoord(0, 1, 0)
  HybridBody1.AppendHybridShape HybridShapePointCoord2
  UpdateObjectErr wPart, HybridShapePointCoord2, wPart.name & "/" & HybridBody1.name & "/" & HybridShapePointCoord2.name
  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  UpdateObjectErr wPart, absPlane, wPart.name & "/" & HybridBody1.name & "/" & absPlane.name
  Set absRef = wPart.CreateReferenceFromGeometry(absPlane)

  Set datpoint1 = hypFact.AddNewPointDatum(Reference0)
  HybridBody1.AppendHybridShape datpoint1
  Set datpoint2 = hypFact.AddNewPointDatum(Reference1)
  HybridBody1.AppendHybridShape datpoint2
  Set datpoint3 = hypFact.AddNewPointDatum(Reference2)
  HybridBody1.AppendHybridShape datpoint3
  Set datplane1 = hypFact.AddNewPlaneDatum(absRef)
  HybridBody1.AppendHybridShape datplane1

  hypFact.DeleteObjectForDatum Reference0
  hypFact.DeleteObjectForDatum Reference1
  hypFact.DeleteObjectForDatum Reference2
  hypFact.DeleteObjectForDatum absRef

  Set absdatRef = wPart.CreateReferenceFromGeometry(datplane1)

  UpdatePartErr wPart, wPart.name & "/" & HybridBody1.name
  wPart.InWorkObject = backWork
  Set toolCall6=absdatRef
End Function

Function toolCall7(wpart,body,absref)
  UpdateObjectErr wPart, Body, wPart.name & "/" & Body.name
  Set sketch = Body.Sketches.Add(absRef)
  CATIA.ActiveDocument.Selection.Clear
  CATIA.ActiveDocument.Selection.Add(sketch)
  CATIA.ActiveDocument.Selection.VisProperties.SetShow(1)
  CATIA.ActiveDocument.Selection.Clear

  Set factory2d = sketch.OpenEdition
  Set Axis2D7 = Sketch.AbsoluteAxis
  Set Line2D8 = Axis2D7.HorizontalReference
  Line2D8.ReportName = 1
  Set Line2D9 = Axis2D7.VerticalReference
  Line2D9.ReportName = 2
  Set constraints1 = Sketch.Constraints

  Set startPoint = Factory2D.CreatePoint(-0.3, 6.5)
  Set endPoint = Factory2D.CreatePoint(0, 6.5)
  Set line = factory2d.CreateLine(-0.3, 6.5, 0, 6.5)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(0, 6.5)
  Set endPoint = Factory2D.CreatePoint(0, 6.8)
  Set line = factory2d.CreateLine(0, 6.5, 0, 6.8)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(0, 6.8)
  Set endPoint = Factory2D.CreatePoint(-0.3, 6.5)
  Set line = factory2d.CreateLine(0, 6.8, -0.3, 6.5)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set pk1 = Factory2D.CreatePoint(500, 0)
  Set pk2 = Factory2D.CreatePoint(-500, 0)
  Set line = Factory2d.CreateLine(500, 0, -500, 0)
  sketch.CenterLine = line
  Set ref1 = wpart.CreateReferenceFromObject(pk1)
  Set ref2 = wpart.CreateReferenceFromObject(pk2)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Sketch.CloseEdition
  UpdateObjectErr wpart, Sketch, wPart.name & "/" & Body.name & "/" & Sketch.name
  Set sketch10 = sketch
  Set toolCall7=sketch10
End Function

Function toolCall8(wpart,HybridBody1)
  set backWork = wPart.InWorkObject 
  UpdateObjectErr wPart, HybridBody1, wPart.name & "/" & HybridBody1.name
  Set hypFact = wPart.HybridShapeFactory
  Set HybridShapePointCoord0 = hypFact.AddNewPointCoord(0, 0, 0)
  HybridBody1.AppendHybridShape HybridShapePointCoord0
  UpdateObjectErr wPart, HybridShapePointCoord0, wPart.name & "/" & HybridBody1.name & "/" & HybridShapePointCoord0.name
  Set HybridShapePointCoord1 = hypFact.AddNewPointCoord(0, 0, -1)
  HybridBody1.AppendHybridShape HybridShapePointCoord1
  UpdateObjectErr wPart, HybridShapePointCoord1, wPart.name & "/" & HybridBody1.name & "/" & HybridShapePointCoord1.name
  Set HybridShapePointCoord2 = hypFact.AddNewPointCoord(0, 1, 0)
  HybridBody1.AppendHybridShape HybridShapePointCoord2
  UpdateObjectErr wPart, HybridShapePointCoord2, wPart.name & "/" & HybridBody1.name & "/" & HybridShapePointCoord2.name
  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  UpdateObjectErr wPart, absPlane, wPart.name & "/" & HybridBody1.name & "/" & absPlane.name
  Set absRef = wPart.CreateReferenceFromGeometry(absPlane)

  Set datpoint1 = hypFact.AddNewPointDatum(Reference0)
  HybridBody1.AppendHybridShape datpoint1
  Set datpoint2 = hypFact.AddNewPointDatum(Reference1)
  HybridBody1.AppendHybridShape datpoint2
  Set datpoint3 = hypFact.AddNewPointDatum(Reference2)
  HybridBody1.AppendHybridShape datpoint3
  Set datplane1 = hypFact.AddNewPlaneDatum(absRef)
  HybridBody1.AppendHybridShape datplane1

  hypFact.DeleteObjectForDatum Reference0
  hypFact.DeleteObjectForDatum Reference1
  hypFact.DeleteObjectForDatum Reference2
  hypFact.DeleteObjectForDatum absRef

  Set absdatRef = wPart.CreateReferenceFromGeometry(datplane1)

  UpdatePartErr wPart, wPart.name & "/" & HybridBody1.name
  wPart.InWorkObject = backWork
  Set toolCall8=absdatRef
End Function

Function toolCall9(wpart,body,absref)
  UpdateObjectErr wPart, Body, wPart.name & "/" & Body.name
  Set sketch = Body.Sketches.Add(absRef)
  CATIA.ActiveDocument.Selection.Clear
  CATIA.ActiveDocument.Selection.Add(sketch)
  CATIA.ActiveDocument.Selection.VisProperties.SetShow(1)
  CATIA.ActiveDocument.Selection.Clear

  Set factory2d = sketch.OpenEdition
  Set Axis2D7 = Sketch.AbsoluteAxis
  Set Line2D8 = Axis2D7.HorizontalReference
  Line2D8.ReportName = 1
  Set Line2D9 = Axis2D7.VerticalReference
  Line2D9.ReportName = 2
  Set constraints1 = Sketch.Constraints

  Set startPoint = Factory2D.CreatePoint(-29, 6.79999999999994)
  Set endPoint = Factory2D.CreatePoint(-29, 6.49999999999994)
  Set line = factory2d.CreateLine(-29, 6.79999999999994, -29, 6.49999999999994)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-29, 6.49999999999994)
  Set endPoint = Factory2D.CreatePoint(-28.7, 6.49999999999994)
  Set line = factory2d.CreateLine(-29, 6.49999999999994, -28.7, 6.49999999999994)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-28.7, 6.49999999999994)
  Set endPoint = Factory2D.CreatePoint(-29, 6.79999999999994)
  Set line = factory2d.CreateLine(-28.7, 6.49999999999994, -29, 6.79999999999994)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set pk1 = Factory2D.CreatePoint(500, 0)
  Set pk2 = Factory2D.CreatePoint(-500, 0)
  Set line = Factory2d.CreateLine(500, 0, -500, 0)
  sketch.CenterLine = line
  Set ref1 = wpart.CreateReferenceFromObject(pk1)
  Set ref2 = wpart.CreateReferenceFromObject(pk2)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Sketch.CloseEdition
  UpdateObjectErr wpart, Sketch, wPart.name & "/" & Body.name & "/" & Sketch.name
  Set sketch12 = sketch
  Set toolCall9=sketch12
End Function

Function toolCall10(wpart,HybridBody1)
  set backWork = wPart.InWorkObject 
  UpdateObjectErr wPart, HybridBody1, wPart.name & "/" & HybridBody1.name
  Set hypFact = wPart.HybridShapeFactory
  Set HybridShapePointCoord0 = hypFact.AddNewPointCoord(0, 0, 22)
  HybridBody1.AppendHybridShape HybridShapePointCoord0
  UpdateObjectErr wPart, HybridShapePointCoord0, wPart.name & "/" & HybridBody1.name & "/" & HybridShapePointCoord0.name
  Set HybridShapePointCoord1 = hypFact.AddNewPointCoord(1, 0, 22)
  HybridBody1.AppendHybridShape HybridShapePointCoord1
  UpdateObjectErr wPart, HybridShapePointCoord1, wPart.name & "/" & HybridBody1.name & "/" & HybridShapePointCoord1.name
  Set HybridShapePointCoord2 = hypFact.AddNewPointCoord(0, 1, 22)
  HybridBody1.AppendHybridShape HybridShapePointCoord2
  UpdateObjectErr wPart, HybridShapePointCoord2, wPart.name & "/" & HybridBody1.name & "/" & HybridShapePointCoord2.name
  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  UpdateObjectErr wPart, absPlane, wPart.name & "/" & HybridBody1.name & "/" & absPlane.name
  Set absRef = wPart.CreateReferenceFromGeometry(absPlane)

  Set datpoint1 = hypFact.AddNewPointDatum(Reference0)
  HybridBody1.AppendHybridShape datpoint1
  Set datpoint2 = hypFact.AddNewPointDatum(Reference1)
  HybridBody1.AppendHybridShape datpoint2
  Set datpoint3 = hypFact.AddNewPointDatum(Reference2)
  HybridBody1.AppendHybridShape datpoint3
  Set datplane1 = hypFact.AddNewPlaneDatum(absRef)
  HybridBody1.AppendHybridShape datplane1

  hypFact.DeleteObjectForDatum Reference0
  hypFact.DeleteObjectForDatum Reference1
  hypFact.DeleteObjectForDatum Reference2
  hypFact.DeleteObjectForDatum absRef

  Set absdatRef = wPart.CreateReferenceFromGeometry(datplane1)

  UpdatePartErr wPart, wPart.name & "/" & HybridBody1.name
  wPart.InWorkObject = backWork
  Set toolCall10=absdatRef
End Function

Function toolCall11(wpart,body,absref)
  UpdateObjectErr wPart, Body, wPart.name & "/" & Body.name
  Set sketch = Body.Sketches.Add(absRef)
  CATIA.ActiveDocument.Selection.Clear
  CATIA.ActiveDocument.Selection.Add(sketch)
  CATIA.ActiveDocument.Selection.VisProperties.SetShow(1)
  CATIA.ActiveDocument.Selection.Clear

  Set factory2d = sketch.OpenEdition
  Set Axis2D7 = Sketch.AbsoluteAxis
  Set Line2D8 = Axis2D7.HorizontalReference
  Line2D8.ReportName = 1
  Set Line2D9 = Axis2D7.VerticalReference
  Line2D9.ReportName = 2
  Set constraints1 = Sketch.Constraints

  Set startPoint = Factory2D.CreatePoint(0, 0)
  Set endPoint = Factory2D.CreatePoint(-2.4585, 0)
  Set line = factory2d.CreateLine(0, 0, -2.4585, 0)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-2.4585, 0)
  Set endPoint = Factory2D.CreatePoint(-2.4585, 23.4585)
  Set line = factory2d.CreateLine(-2.4585, 0, -2.4585, 23.4585)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-2.4585, 23.4585)
  Set endPoint = Factory2D.CreatePoint(-3, 24)
  Set line = factory2d.CreateLine(-2.4585, 23.4585, -3, 24)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-3, 24)
  Set endPoint = Factory2D.CreatePoint(0, 24)
  Set line = factory2d.CreateLine(-3, 24, 0, 24)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(0, 24)
  Set endPoint = Factory2D.CreatePoint(0, 0)
  Set line = factory2d.CreateLine(0, 24, 0, 0)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set pk1 = Factory2D.CreatePoint(0, 24)
  Set pk2 = Factory2D.CreatePoint(0, 0)
  Set line = Factory2d.CreateLine(0, 24, 0, 0)
  sketch.CenterLine = line
  Set ref1 = wpart.CreateReferenceFromObject(pk1)
  Set ref2 = wpart.CreateReferenceFromObject(pk2)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Sketch.CloseEdition
  UpdateObjectErr wpart, Sketch, wPart.name & "/" & Body.name & "/" & Sketch.name
  Set sketch17 = sketch
  Set toolCall11=sketch17
End Function

Function toolCall13(wpart,HybridBody1)
  set backWork = wPart.InWorkObject 
  UpdateObjectErr wPart, HybridBody1, wPart.name & "/" & HybridBody1.name
  Set hypFact = wPart.HybridShapeFactory
  Set HybridShapePointCoord0 = hypFact.AddNewPointCoord(0, 24, 22)
  HybridBody1.AppendHybridShape HybridShapePointCoord0
  UpdateObjectErr wPart, HybridShapePointCoord0, wPart.name & "/" & HybridBody1.name & "/" & HybridShapePointCoord0.name
  Set HybridShapePointCoord1 = hypFact.AddNewPointCoord(1, 24, 22)
  HybridBody1.AppendHybridShape HybridShapePointCoord1
  UpdateObjectErr wPart, HybridShapePointCoord1, wPart.name & "/" & HybridBody1.name & "/" & HybridShapePointCoord1.name
  Set HybridShapePointCoord2 = hypFact.AddNewPointCoord(0, 24, 23)
  HybridBody1.AppendHybridShape HybridShapePointCoord2
  UpdateObjectErr wPart, HybridShapePointCoord2, wPart.name & "/" & HybridBody1.name & "/" & HybridShapePointCoord2.name
  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  UpdateObjectErr wPart, absPlane, wPart.name & "/" & HybridBody1.name & "/" & absPlane.name
  Set absRef = wPart.CreateReferenceFromGeometry(absPlane)

  Set datpoint1 = hypFact.AddNewPointDatum(Reference0)
  HybridBody1.AppendHybridShape datpoint1
  Set datpoint2 = hypFact.AddNewPointDatum(Reference1)
  HybridBody1.AppendHybridShape datpoint2
  Set datpoint3 = hypFact.AddNewPointDatum(Reference2)
  HybridBody1.AppendHybridShape datpoint3
  Set datplane1 = hypFact.AddNewPlaneDatum(absRef)
  HybridBody1.AppendHybridShape datplane1

  hypFact.DeleteObjectForDatum Reference0
  hypFact.DeleteObjectForDatum Reference1
  hypFact.DeleteObjectForDatum Reference2
  hypFact.DeleteObjectForDatum absRef

  Set absdatRef = wPart.CreateReferenceFromGeometry(datplane1)

  UpdatePartErr wPart, wPart.name & "/" & HybridBody1.name
  wPart.InWorkObject = backWork
  Set toolCall13=absdatRef
End Function

Function toolCall12(partdocument,wpart,body,HybridBody1)
  set thread=nothing
  isfaceconic = 0
  set cylCatiaFace=GetFaceReferenceByPoint(partdocument,wpart,body,0,14.97925,19.5415,0,-1,0,0.01,isfaceconic)
  if not cylCatiaFace is nothing then
     Set HybridBody1 = HybridBody1
  Set absref=toolCall13(wpart,HybridBody1)
     set plaCatiaFace=absref
  If isfaceconic > 0 then
     Set hypFact = wPart.HybridShapeFactory
     Set HybridShapePointCoord0 = hypFact.AddNewPointCoord(0,23.4585,19.5415)
     HybridBody1.AppendHybridShape HybridShapePointCoord0
     UpdateObjectErr wPart, HybridShapePointCoord0, wPart.name & "/" & HybridBody1.name & "/" & HybridShapePointCoord0.name
     Set HybridShapePointCoord1 = hypFact.AddNewPointCoord(0,6.5,19.5415)
     HybridBody1.AppendHybridShape HybridShapePointCoord1
     UpdateObjectErr wPart, HybridShapePointCoord1, wPart.name & "/" & HybridBody1.name & "/" & HybridShapePointCoord1.name
     Set Reference0 = wPart.CreateReferenceFromGeometry(HybridShapePointCoord0)
     Set Reference1 = wPart.CreateReferenceFromGeometry(HybridShapePointCoord1)
     Set threadfeatureline = hypFact.AddNewLinePtPt(Reference0, Reference1)
     HybridBody1.AppendHybridShape threadfeatureline
     UpdateObjectErr wPart, threadfeatureline, wPart.name & "/" & HybridBody1.name & "/" & threadfeatureline.name
     Set threadfeaturelineRef = wPart.CreateReferenceFromGeometry(threadfeatureline)
     Set intersectionRef = hypFact.AddNewIntersection(threadfeaturelineRef,plaCatiaFace)
     intersectionRef.ExtendMode = 1
     hybridBody1.AppendHybridShape intersectionRef
     UpdateObjectErr wPart, intersectionRef, wPart.name & "/" & HybridBody1.name & "/" & intersectionRef.name
     Set HybridShapePointCoord3 = hypFact.AddNewPointCoord(0,24,22)
     HybridBody1.AppendHybridShape HybridShapePointCoord3
     UpdateObjectErr wPart, HybridShapePointCoord3, wPart.name & "/" & HybridBody1.name & "/" & HybridShapePointCoord3.name
     set spaworkbench = CATIA.ActiveDocument.GetWorkbench("SPAWorkbench")
     set pointmeasure = spaworkbench.GetMeasurable(HybridShapePointCoord3)
     Distance = pointmeasure.GetMinimumDistance(intersectionRef)
     hypFact.DeleteObjectForDatum intersectionRef
     hypFact.DeleteObjectForDatum threadfeaturelineRef
     hypFact.DeleteObjectForDatum Reference0
     hypFact.DeleteObjectForDatum Reference1
     hypFact.DeleteObjectForDatum HybridShapePointCoord3
  End If    
    if not cylCatiaFace is nothing then
      wPart.InWorkObject = Body
      Set thread = wpart.ShapeFactory.AddNewThreadWithOutRef()
      thread.Diameter = 6
      thread.Pitch = 1
      thread.Depth = 17.5
      thread.LateralFaceElement = cylCatiaFace
      thread.LimitFaceElement = plaCatiaFace
      thread.name = "M6"
      on error resume next
      wpart.Update
      if err.number<> 0 then 
        err.clear()
        thread.Depth = 17.22925
        wpart.Update
        if err.number<> 0 then 
          err.clear()
          thread.Depth = 16.9585
          wpart.Update
          if err.number<> 0 then 
            wpart.Inactivate thread
          end if
        end if
      end if
      on error goto 0
    end if
  end if

  Set toolCall12=thread
End Function

Function toolCall14(wpart,HybridBody2)
  set backWork = wPart.InWorkObject 
  UpdateObjectErr wPart, HybridBody2, wPart.name & "/" & HybridBody2.name
  Set hypFact = wPart.HybridShapeFactory
  Set HybridShapePointCoord0 = hypFact.AddNewPointCoord(0, 0, 0)
  HybridShapePointCoord0.Name = "PointOfCoincidenceStart:b"
  HybridBody2.AppendHybridShape HybridShapePointCoord0
  UpdateObjectErr wPart, HybridShapePointCoord0, wPart.name & "/" & HybridBody2.name & "/" & HybridShapePointCoord0.name
  Set HybridShapePointCoord1 = hypFact.AddNewPointCoord(1, 0, 0)
  HybridShapePointCoord1.Name = "PointOfCoincidenceEnd_X:b"
  HybridBody2.AppendHybridShape HybridShapePointCoord1
  UpdateObjectErr wPart, HybridShapePointCoord1, wPart.name & "/" & HybridBody2.name & "/" & HybridShapePointCoord1.name
  Set HybridShapePointCoord2 = hypFact.AddNewPointCoord(0, 1, 0)
  HybridShapePointCoord2.Name = "PointOfCoincidenceEnd_Y:b"
  HybridBody2.AppendHybridShape HybridShapePointCoord2
  UpdateObjectErr wPart, HybridShapePointCoord2, wPart.name & "/" & HybridBody2.name & "/" & HybridShapePointCoord2.name
  Set HybridShapePointCoord3 = hypFact.AddNewPointCoord(0, 0, 1)
  HybridShapePointCoord3.Name = "PointOfCoincidenceEnd_Z:b"
  HybridBody2.AppendHybridShape HybridShapePointCoord3
  UpdateObjectErr wPart, HybridShapePointCoord3, wPart.name & "/" & HybridBody2.name & "/" & HybridShapePointCoord3.name
  Set Reference0 = wPart.CreateReferenceFromGeometry(HybridShapePointCoord0)
  Set Reference1 = wPart.CreateReferenceFromGeometry(HybridShapePointCoord1)
  Set Reference2 = wPart.CreateReferenceFromGeometry(HybridShapePointCoord2)
  Set Reference3 = wPart.CreateReferenceFromGeometry(HybridShapePointCoord3)
  Set absPlaneOXY = hypFact.AddNewPlane3Points(Reference0, Reference1, Reference2)
  absPlaneOXY.Name = "PlaneOffset:b"
  HybridBody2.AppendHybridShape absPlaneOXY
  UpdateObjectErr wPart, absPlaneOXY, wPart.name & "/" & HybridBody2.name & "/" & absPlaneOXY.name
  Set absPlaneOXZ = hypFact.AddNewPlane3Points(Reference0, Reference3, Reference1)
  absPlaneOXZ.Name = "PlaneAngular:b"
  HybridBody2.AppendHybridShape absPlaneOXZ
  UpdateObjectErr wPart, absPlaneOXZ, wPart.name & "/" & HybridBody2.name & "/" & absPlaneOXZ.name
  Set lineOX = hypFact.AddNewLinePtPt(Reference0, Reference1)
  lineOX.Name = "LineCoincidence_X:b"
  HybridBody2.AppendHybridShape lineOX
  UpdateObjectErr wPart, lineOX, wPart.name & "/" & HybridBody2.name & "/" & lineOX.name
  Set lineOY = hypFact.AddNewLinePtPt(Reference0, Reference2)
  lineOY.Name = "LineCoincidence_Y:b"
  HybridBody2.AppendHybridShape lineOY
  UpdateObjectErr wPart, lineOY, wPart.name & "/" & HybridBody2.name & "/" & lineOY.name
  Set lineOZ = hypFact.AddNewLinePtPt(Reference0, Reference3)
  lineOZ.Name = "LineCoincidence:b"
  HybridBody2.AppendHybridShape lineOZ
  UpdateObjectErr wPart, lineOZ, wPart.name & "/" & HybridBody2.name & "/" & lineOZ.name
  Set absRef = wPart.CreateReferenceFromGeometry(absPlaneOXY)
  UpdatePartErr wPart, wPart.name & "/" & HybridBody2.Name
  wPart.InWorkObject = backWork
  Set toolCall14=absref
End Function

Function toolCall15(wpart,HybridBody2)
  set backWork = wPart.InWorkObject 
  UpdateObjectErr wPart, HybridBody2, wPart.name & "/" & HybridBody2.name
  Set hypFact = wPart.HybridShapeFactory
  Set HybridShapePointCoord0 = hypFact.AddNewPointCoord(0, 6.5, 22)
  HybridShapePointCoord0.Name = "PointOfCoincidenceStart:screw"
  HybridBody2.AppendHybridShape HybridShapePointCoord0
  UpdateObjectErr wPart, HybridShapePointCoord0, wPart.name & "/" & HybridBody2.name & "/" & HybridShapePointCoord0.name
  Set HybridShapePointCoord1 = hypFact.AddNewPointCoord(1, 6.5, 22)
  HybridShapePointCoord1.Name = "PointOfCoincidenceEnd_X:screw"
  HybridBody2.AppendHybridShape HybridShapePointCoord1
  UpdateObjectErr wPart, HybridShapePointCoord1, wPart.name & "/" & HybridBody2.name & "/" & HybridShapePointCoord1.name
  Set HybridShapePointCoord2 = hypFact.AddNewPointCoord(0, 6.5, 21)
  HybridShapePointCoord2.Name = "PointOfCoincidenceEnd_Y:screw"
  HybridBody2.AppendHybridShape HybridShapePointCoord2
  UpdateObjectErr wPart, HybridShapePointCoord2, wPart.name & "/" & HybridBody2.name & "/" & HybridShapePointCoord2.name
  Set HybridShapePointCoord3 = hypFact.AddNewPointCoord(0, 7.5, 22)
  HybridShapePointCoord3.Name = "PointOfCoincidenceEnd_Z:screw"
  HybridBody2.AppendHybridShape HybridShapePointCoord3
  UpdateObjectErr wPart, HybridShapePointCoord3, wPart.name & "/" & HybridBody2.name & "/" & HybridShapePointCoord3.name
  Set Reference0 = wPart.CreateReferenceFromGeometry(HybridShapePointCoord0)
  Set Reference1 = wPart.CreateReferenceFromGeometry(HybridShapePointCoord1)
  Set Reference2 = wPart.CreateReferenceFromGeometry(HybridShapePointCoord2)
  Set Reference3 = wPart.CreateReferenceFromGeometry(HybridShapePointCoord3)
  Set absPlaneOXY = hypFact.AddNewPlane3Points(Reference0, Reference1, Reference2)
  absPlaneOXY.Name = "PlaneOffset:screw"
  HybridBody2.AppendHybridShape absPlaneOXY
  UpdateObjectErr wPart, absPlaneOXY, wPart.name & "/" & HybridBody2.name & "/" & absPlaneOXY.name
  Set absPlaneOXZ = hypFact.AddNewPlane3Points(Reference0, Reference3, Reference1)
  absPlaneOXZ.Name = "PlaneAngular:screw"
  HybridBody2.AppendHybridShape absPlaneOXZ
  UpdateObjectErr wPart, absPlaneOXZ, wPart.name & "/" & HybridBody2.name & "/" & absPlaneOXZ.name
  Set lineOX = hypFact.AddNewLinePtPt(Reference0, Reference1)
  lineOX.Name = "LineCoincidence_X:screw"
  HybridBody2.AppendHybridShape lineOX
  UpdateObjectErr wPart, lineOX, wPart.name & "/" & HybridBody2.name & "/" & lineOX.name
  Set lineOY = hypFact.AddNewLinePtPt(Reference0, Reference2)
  lineOY.Name = "LineCoincidence_Y:screw"
  HybridBody2.AppendHybridShape lineOY
  UpdateObjectErr wPart, lineOY, wPart.name & "/" & HybridBody2.name & "/" & lineOY.name
  Set lineOZ = hypFact.AddNewLinePtPt(Reference0, Reference3)
  lineOZ.Name = "LineCoincidence:screw"
  HybridBody2.AppendHybridShape lineOZ
  UpdateObjectErr wPart, lineOZ, wPart.name & "/" & HybridBody2.name & "/" & lineOZ.name
  Set absRef = wPart.CreateReferenceFromGeometry(absPlaneOXY)
  UpdatePartErr wPart, wPart.name & "/" & HybridBody2.Name
  wPart.InWorkObject = backWork
  Set toolCall15=absref
End Function

Function toolCall16(wpart,HybridBody2)
  set backWork = wPart.InWorkObject 
  UpdateObjectErr wPart, HybridBody2, wPart.name & "/" & HybridBody2.name
  Set hypFact = wPart.HybridShapeFactory
  Set HybridShapePointCoord0 = hypFact.AddNewPointCoord(0, 0, 0)
  HybridShapePointCoord0.Name = "PointOfCoincidenceStart:turn_around"
  HybridBody2.AppendHybridShape HybridShapePointCoord0
  UpdateObjectErr wPart, HybridShapePointCoord0, wPart.name & "/" & HybridBody2.name & "/" & HybridShapePointCoord0.name
  Set HybridShapePointCoord1 = hypFact.AddNewPointCoord(0, 0, -1)
  HybridShapePointCoord1.Name = "PointOfCoincidenceEnd_X:turn_around"
  HybridBody2.AppendHybridShape HybridShapePointCoord1
  UpdateObjectErr wPart, HybridShapePointCoord1, wPart.name & "/" & HybridBody2.name & "/" & HybridShapePointCoord1.name
  Set HybridShapePointCoord2 = hypFact.AddNewPointCoord(-1.22464679914735e-16, -1, 0)
  HybridShapePointCoord2.Name = "PointOfCoincidenceEnd_Y:turn_around"
  HybridBody2.AppendHybridShape HybridShapePointCoord2
  UpdateObjectErr wPart, HybridShapePointCoord2, wPart.name & "/" & HybridBody2.name & "/" & HybridShapePointCoord2.name
  Set HybridShapePointCoord3 = hypFact.AddNewPointCoord(-1, 1.22464679914735e-16, 0)
  HybridShapePointCoord3.Name = "PointOfCoincidenceEnd_Z:turn_around"
  HybridBody2.AppendHybridShape HybridShapePointCoord3
  UpdateObjectErr wPart, HybridShapePointCoord3, wPart.name & "/" & HybridBody2.name & "/" & HybridShapePointCoord3.name
  Set Reference0 = wPart.CreateReferenceFromGeometry(HybridShapePointCoord0)
  Set Reference1 = wPart.CreateReferenceFromGeometry(HybridShapePointCoord1)
  Set Reference2 = wPart.CreateReferenceFromGeometry(HybridShapePointCoord2)
  Set Reference3 = wPart.CreateReferenceFromGeometry(HybridShapePointCoord3)
  Set absPlaneOXY = hypFact.AddNewPlane3Points(Reference0, Reference1, Reference2)
  absPlaneOXY.Name = "PlaneOffset:turn_around"
  HybridBody2.AppendHybridShape absPlaneOXY
  UpdateObjectErr wPart, absPlaneOXY, wPart.name & "/" & HybridBody2.name & "/" & absPlaneOXY.name
  Set absPlaneOXZ = hypFact.AddNewPlane3Points(Reference0, Reference3, Reference1)
  absPlaneOXZ.Name = "PlaneAngular:turn_around"
  HybridBody2.AppendHybridShape absPlaneOXZ
  UpdateObjectErr wPart, absPlaneOXZ, wPart.name & "/" & HybridBody2.name & "/" & absPlaneOXZ.name
  Set lineOX = hypFact.AddNewLinePtPt(Reference0, Reference1)
  lineOX.Name = "LineCoincidence_X:turn_around"
  HybridBody2.AppendHybridShape lineOX
  UpdateObjectErr wPart, lineOX, wPart.name & "/" & HybridBody2.name & "/" & lineOX.name
  Set lineOY = hypFact.AddNewLinePtPt(Reference0, Reference2)
  lineOY.Name = "LineCoincidence_Y:turn_around"
  HybridBody2.AppendHybridShape lineOY
  UpdateObjectErr wPart, lineOY, wPart.name & "/" & HybridBody2.name & "/" & lineOY.name
  Set lineOZ = hypFact.AddNewLinePtPt(Reference0, Reference3)
  lineOZ.Name = "LineCoincidence:turn_around"
  HybridBody2.AppendHybridShape lineOZ
  UpdateObjectErr wPart, lineOZ, wPart.name & "/" & HybridBody2.name & "/" & lineOZ.name
  Set absRef = wPart.CreateReferenceFromGeometry(absPlaneOXY)
  UpdatePartErr wPart, wPart.name & "/" & HybridBody2.Name
  wPart.InWorkObject = backWork
  Set toolCall16=absref
End Function

Function toolCall17(wpart,HybridBody1)
  set backWork = wPart.InWorkObject 
  UpdateObjectErr wPart, HybridBody1, wPart.name & "/" & HybridBody1.name
  Set hypFact = wPart.HybridShapeFactory
  Set HybridShapePointCoord0 = hypFact.AddNewPointCoord(0, 0, 0)
  HybridBody1.AppendHybridShape HybridShapePointCoord0
  UpdateObjectErr wPart, HybridShapePointCoord0, wPart.name & "/" & HybridBody1.name & "/" & HybridShapePointCoord0.name
  Set HybridShapePointCoord1 = hypFact.AddNewPointCoord(1, 0, 0)
  HybridBody1.AppendHybridShape HybridShapePointCoord1
  UpdateObjectErr wPart, HybridShapePointCoord1, wPart.name & "/" & HybridBody1.name & "/" & HybridShapePointCoord1.name
  Set HybridShapePointCoord2 = hypFact.AddNewPointCoord(0, 1, 0)
  HybridBody1.AppendHybridShape HybridShapePointCoord2
  UpdateObjectErr wPart, HybridShapePointCoord2, wPart.name & "/" & HybridBody1.name & "/" & HybridShapePointCoord2.name
  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  UpdateObjectErr wPart, absPlane, wPart.name & "/" & HybridBody1.name & "/" & absPlane.name
  Set absRef = wPart.CreateReferenceFromGeometry(absPlane)

  Set datpoint1 = hypFact.AddNewPointDatum(Reference0)
  HybridBody1.AppendHybridShape datpoint1
  Set datpoint2 = hypFact.AddNewPointDatum(Reference1)
  HybridBody1.AppendHybridShape datpoint2
  Set datpoint3 = hypFact.AddNewPointDatum(Reference2)
  HybridBody1.AppendHybridShape datpoint3
  Set datplane1 = hypFact.AddNewPlaneDatum(absRef)
  HybridBody1.AppendHybridShape datplane1

  hypFact.DeleteObjectForDatum Reference0
  hypFact.DeleteObjectForDatum Reference1
  hypFact.DeleteObjectForDatum Reference2
  hypFact.DeleteObjectForDatum absRef

  Set absdatRef = wPart.CreateReferenceFromGeometry(datplane1)

  UpdatePartErr wPart, wPart.name & "/" & HybridBody1.name
  wPart.InWorkObject = backWork
  Set toolCall17=absdatRef
End Function

Function toolCall18(wpart,body,absref)
  UpdateObjectErr wPart, Body, wPart.name & "/" & Body.name
  Set sketch = Body.Sketches.Add(absRef)
  CATIA.ActiveDocument.Selection.Clear
  CATIA.ActiveDocument.Selection.Add(sketch)
  CATIA.ActiveDocument.Selection.VisProperties.SetShow(1)
  CATIA.ActiveDocument.Selection.Clear

  Set factory2d = sketch.OpenEdition
  Set Axis2D7 = Sketch.AbsoluteAxis
  Set Line2D8 = Axis2D7.HorizontalReference
  Line2D8.ReportName = 1
  Set Line2D9 = Axis2D7.VerticalReference
  Line2D9.ReportName = 2
  Set constraints1 = Sketch.Constraints

  Set startPoint = Factory2D.CreatePoint(-16, 0)
  Set endPoint = Factory2D.CreatePoint(-16, 2.3865)
  Set line = factory2d.CreateLine(-16, 0, -16, 2.3865)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-16, 2.3865)
  Set endPoint = Factory2D.CreatePoint(-15.3865, 3)
  Set line = factory2d.CreateLine(-16, 2.3865, -15.3865, 3)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-15.3865, 3)
  Set endPoint = Factory2D.CreatePoint(-1, 3)
  Set line = factory2d.CreateLine(-15.3865, 3, -1, 3)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-1, 3)
  Set endPoint = Factory2D.CreatePoint(0, 2)
  Set line = factory2d.CreateLine(-1, 3, 0, 2)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(0, 2)
  Set endPoint = Factory2D.CreatePoint(0, 0)
  Set line = factory2d.CreateLine(0, 2, 0, 0)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(0, 0)
  Set endPoint = Factory2D.CreatePoint(-16, 0)
  Set line = factory2d.CreateLine(0, 0, -16, 0)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set pk1 = Factory2D.CreatePoint(0, 0)
  Set pk2 = Factory2D.CreatePoint(-16, 0)
  Set line = Factory2d.CreateLine(0, 0, -16, 0)
  sketch.CenterLine = line
  Set ref1 = wpart.CreateReferenceFromObject(pk1)
  Set ref2 = wpart.CreateReferenceFromObject(pk2)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Sketch.CloseEdition
  UpdateObjectErr wpart, Sketch, wPart.name & "/" & Body.name & "/" & Sketch.name
  Set sketch3 = sketch
  Set toolCall18=sketch3
End Function

Function toolCall20(wpart,HybridBody1)
  set backWork = wPart.InWorkObject 
  UpdateObjectErr wPart, HybridBody1, wPart.name & "/" & HybridBody1.name
  Set hypFact = wPart.HybridShapeFactory
  Set HybridShapePointCoord0 = hypFact.AddNewPointCoord(-16, 0, 0)
  HybridBody1.AppendHybridShape HybridShapePointCoord0
  UpdateObjectErr wPart, HybridShapePointCoord0, wPart.name & "/" & HybridBody1.name & "/" & HybridShapePointCoord0.name
  Set HybridShapePointCoord1 = hypFact.AddNewPointCoord(-16, 1, 0)
  HybridBody1.AppendHybridShape HybridShapePointCoord1
  UpdateObjectErr wPart, HybridShapePointCoord1, wPart.name & "/" & HybridBody1.name & "/" & HybridShapePointCoord1.name
  Set HybridShapePointCoord2 = hypFact.AddNewPointCoord(-16, 0, 1)
  HybridBody1.AppendHybridShape HybridShapePointCoord2
  UpdateObjectErr wPart, HybridShapePointCoord2, wPart.name & "/" & HybridBody1.name & "/" & HybridShapePointCoord2.name
  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  UpdateObjectErr wPart, absPlane, wPart.name & "/" & HybridBody1.name & "/" & absPlane.name
  Set absRef = wPart.CreateReferenceFromGeometry(absPlane)

  Set datpoint1 = hypFact.AddNewPointDatum(Reference0)
  HybridBody1.AppendHybridShape datpoint1
  Set datpoint2 = hypFact.AddNewPointDatum(Reference1)
  HybridBody1.AppendHybridShape datpoint2
  Set datpoint3 = hypFact.AddNewPointDatum(Reference2)
  HybridBody1.AppendHybridShape datpoint3
  Set datplane1 = hypFact.AddNewPlaneDatum(absRef)
  HybridBody1.AppendHybridShape datplane1

  hypFact.DeleteObjectForDatum Reference0
  hypFact.DeleteObjectForDatum Reference1
  hypFact.DeleteObjectForDatum Reference2
  hypFact.DeleteObjectForDatum absRef

  Set absdatRef = wPart.CreateReferenceFromGeometry(datplane1)

  UpdatePartErr wPart, wPart.name & "/" & HybridBody1.name
  wPart.InWorkObject = backWork
  Set toolCall20=absdatRef
End Function

Function toolCall19(partdocument,wpart,body,HybridBody1)
  set thread=nothing
  isfaceconic = 0
  set cylCatiaFace=GetFaceReferenceByPoint(partdocument,wpart,body,-8.19325,3,0,1,0,0,0.01,isfaceconic)
  if not cylCatiaFace is nothing then
     Set HybridBody1 = HybridBody1
  Set absref=toolCall20(wpart,HybridBody1)
     set plaCatiaFace=absref
  If isfaceconic > 0 then
     Set hypFact = wPart.HybridShapeFactory
     Set HybridShapePointCoord0 = hypFact.AddNewPointCoord(-15.3865,3,0)
     HybridBody1.AppendHybridShape HybridShapePointCoord0
     UpdateObjectErr wPart, HybridShapePointCoord0, wPart.name & "/" & HybridBody1.name & "/" & HybridShapePointCoord0.name
     Set HybridShapePointCoord1 = hypFact.AddNewPointCoord(-1,3,0)
     HybridBody1.AppendHybridShape HybridShapePointCoord1
     UpdateObjectErr wPart, HybridShapePointCoord1, wPart.name & "/" & HybridBody1.name & "/" & HybridShapePointCoord1.name
     Set Reference0 = wPart.CreateReferenceFromGeometry(HybridShapePointCoord0)
     Set Reference1 = wPart.CreateReferenceFromGeometry(HybridShapePointCoord1)
     Set threadfeatureline = hypFact.AddNewLinePtPt(Reference0, Reference1)
     HybridBody1.AppendHybridShape threadfeatureline
     UpdateObjectErr wPart, threadfeatureline, wPart.name & "/" & HybridBody1.name & "/" & threadfeatureline.name
     Set threadfeaturelineRef = wPart.CreateReferenceFromGeometry(threadfeatureline)
     Set intersectionRef = hypFact.AddNewIntersection(threadfeaturelineRef,plaCatiaFace)
     intersectionRef.ExtendMode = 1
     hybridBody1.AppendHybridShape intersectionRef
     UpdateObjectErr wPart, intersectionRef, wPart.name & "/" & HybridBody1.name & "/" & intersectionRef.name
     Set HybridShapePointCoord3 = hypFact.AddNewPointCoord(-16,0,0)
     HybridBody1.AppendHybridShape HybridShapePointCoord3
     UpdateObjectErr wPart, HybridShapePointCoord3, wPart.name & "/" & HybridBody1.name & "/" & HybridShapePointCoord3.name
     set spaworkbench = CATIA.ActiveDocument.GetWorkbench("SPAWorkbench")
     set pointmeasure = spaworkbench.GetMeasurable(HybridShapePointCoord3)
     Distance = pointmeasure.GetMinimumDistance(intersectionRef)
     hypFact.DeleteObjectForDatum intersectionRef
     hypFact.DeleteObjectForDatum threadfeaturelineRef
     hypFact.DeleteObjectForDatum Reference0
     hypFact.DeleteObjectForDatum Reference1
     hypFact.DeleteObjectForDatum HybridShapePointCoord3
  End If    
    if not cylCatiaFace is nothing then
      wPart.InWorkObject = Body
      Set thread = wpart.ShapeFactory.AddNewThreadWithOutRef()
  If isfaceconic > 0 then
      thread.Diameter =  Distance*2
  Else
      thread.Diameter = 6
   End If    
      thread.Pitch = 1
      thread.Depth = 16
      thread.LateralFaceElement = cylCatiaFace
      thread.LimitFaceElement = plaCatiaFace
      thread.name = "M6"
      on error resume next
      wpart.Update
      if err.number<> 0 then 
        err.clear()
        thread.Depth = 15.19325
        wpart.Update
        if err.number<> 0 then 
          err.clear()
          thread.Depth = 14.3865
          wpart.Update
          if err.number<> 0 then 
            wpart.Inactivate thread
          end if
        end if
      end if
      on error goto 0
    end if
  end if

  Set toolCall19=thread
End Function

Function toolCall21(wpart,HybridBody1)
  set backWork = wPart.InWorkObject 
  UpdateObjectErr wPart, HybridBody1, wPart.name & "/" & HybridBody1.name
  Set hypFact = wPart.HybridShapeFactory
  Set HybridShapePointCoord0 = hypFact.AddNewPointCoord(-16, 0, 0)
  HybridBody1.AppendHybridShape HybridShapePointCoord0
  UpdateObjectErr wPart, HybridShapePointCoord0, wPart.name & "/" & HybridBody1.name & "/" & HybridShapePointCoord0.name
  Set HybridShapePointCoord1 = hypFact.AddNewPointCoord(-16, 1, 0)
  HybridBody1.AppendHybridShape HybridShapePointCoord1
  UpdateObjectErr wPart, HybridShapePointCoord1, wPart.name & "/" & HybridBody1.name & "/" & HybridShapePointCoord1.name
  Set HybridShapePointCoord2 = hypFact.AddNewPointCoord(-16, 0, -1)
  HybridBody1.AppendHybridShape HybridShapePointCoord2
  UpdateObjectErr wPart, HybridShapePointCoord2, wPart.name & "/" & HybridBody1.name & "/" & HybridShapePointCoord2.name
  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  UpdateObjectErr wPart, absPlane, wPart.name & "/" & HybridBody1.name & "/" & absPlane.name
  Set absRef = wPart.CreateReferenceFromGeometry(absPlane)

  Set datpoint1 = hypFact.AddNewPointDatum(Reference0)
  HybridBody1.AppendHybridShape datpoint1
  Set datpoint2 = hypFact.AddNewPointDatum(Reference1)
  HybridBody1.AppendHybridShape datpoint2
  Set datpoint3 = hypFact.AddNewPointDatum(Reference2)
  HybridBody1.AppendHybridShape datpoint3
  Set datplane1 = hypFact.AddNewPlaneDatum(absRef)
  HybridBody1.AppendHybridShape datplane1

  hypFact.DeleteObjectForDatum Reference0
  hypFact.DeleteObjectForDatum Reference1
  hypFact.DeleteObjectForDatum Reference2
  hypFact.DeleteObjectForDatum absRef

  Set absdatRef = wPart.CreateReferenceFromGeometry(datplane1)

  UpdatePartErr wPart, wPart.name & "/" & HybridBody1.name
  wPart.InWorkObject = backWork
  Set toolCall21=absdatRef
End Function

Function toolCall22(wpart,body,absref)
  UpdateObjectErr wPart, Body, wPart.name & "/" & Body.name
  Set sketch = Body.Sketches.Add(absRef)
  CATIA.ActiveDocument.Selection.Clear
  CATIA.ActiveDocument.Selection.Add(sketch)
  CATIA.ActiveDocument.Selection.VisProperties.SetShow(1)
  CATIA.ActiveDocument.Selection.Clear

  Set factory2d = sketch.OpenEdition
  Set Axis2D7 = Sketch.AbsoluteAxis
  Set Line2D8 = Axis2D7.HorizontalReference
  Line2D8.ReportName = 1
  Set Line2D9 = Axis2D7.VerticalReference
  Line2D9.ReportName = 2
  Set constraints1 = Sketch.Constraints

  Set startPoint = Factory2D.CreatePoint(-1.5, -0.866025403784439)
  Set endPoint = Factory2D.CreatePoint(0, -1.73205080756888)
  Set line = factory2d.CreateLine(-1.5, -0.866025403784439, 0, -1.73205080756888)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(0, -1.73205080756888)
  Set endPoint = Factory2D.CreatePoint(1.5, -0.866025403784439)
  Set line = factory2d.CreateLine(0, -1.73205080756888, 1.5, -0.866025403784439)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(1.5, -0.866025403784439)
  Set endPoint = Factory2D.CreatePoint(1.5, 0.866025403784439)
  Set line = factory2d.CreateLine(1.5, -0.866025403784439, 1.5, 0.866025403784439)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(1.5, 0.866025403784439)
  Set endPoint = Factory2D.CreatePoint(0, 1.73205080756888)
  Set line = factory2d.CreateLine(1.5, 0.866025403784439, 0, 1.73205080756888)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(0, 1.73205080756888)
  Set endPoint = Factory2D.CreatePoint(-1.5, 0.866025403784439)
  Set line = factory2d.CreateLine(0, 1.73205080756888, -1.5, 0.866025403784439)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-1.5, 0.866025403784439)
  Set endPoint = Factory2D.CreatePoint(-1.5, -0.866025403784439)
  Set line = factory2d.CreateLine(-1.5, 0.866025403784439, -1.5, -0.866025403784439)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Sketch.CloseEdition
  UpdateObjectErr wpart, Sketch, wPart.name & "/" & Body.name & "/" & Sketch.name
  Set sketch5 = sketch
  Set toolCall22=sketch5
End Function

Function toolCall23(wpart,HybridBody1)
  set backWork = wPart.InWorkObject 
  UpdateObjectErr wPart, HybridBody1, wPart.name & "/" & HybridBody1.name
  Set hypFact = wPart.HybridShapeFactory
  Set HybridShapePointCoord0 = hypFact.AddNewPointCoord(0, 0, 0)
  HybridBody1.AppendHybridShape HybridShapePointCoord0
  UpdateObjectErr wPart, HybridShapePointCoord0, wPart.name & "/" & HybridBody1.name & "/" & HybridShapePointCoord0.name
  Set HybridShapePointCoord1 = hypFact.AddNewPointCoord(1, 0, 0)
  HybridBody1.AppendHybridShape HybridShapePointCoord1
  UpdateObjectErr wPart, HybridShapePointCoord1, wPart.name & "/" & HybridBody1.name & "/" & HybridShapePointCoord1.name
  Set HybridShapePointCoord2 = hypFact.AddNewPointCoord(0, 1, 0)
  HybridBody1.AppendHybridShape HybridShapePointCoord2
  UpdateObjectErr wPart, HybridShapePointCoord2, wPart.name & "/" & HybridBody1.name & "/" & HybridShapePointCoord2.name
  Set Reference0 = wPart.CreateReferenceFromGeometry(HybridShapePointCoord0)
  Set Reference1 = wPart.CreateReferenceFromGeometry(HybridShapePointCoord1)
  Set Reference2 = wPart.CreateReferenceFromGeometry(HybridShapePointCoord2)
  Set absPlane = hypFact.AddNewPlane3Points(Reference0, Reference1, Reference2)
  HybridBody1.AppendHybridShape absPlane
  UpdateObjectErr wPart, absPlane, wPart.name & "/" & HybridBody1.name & "/" & absPlane.name
  Set absRef = wPart.CreateReferenceFromGeometry(absPlane)

  Set datpoint1 = hypFact.AddNewPointDatum(Reference0)
  HybridBody1.AppendHybridShape datpoint1
  Set datpoint2 = hypFact.AddNewPointDatum(Reference1)
  HybridBody1.AppendHybridShape datpoint2
  Set datpoint3 = hypFact.AddNewPointDatum(Reference2)
  HybridBody1.AppendHybridShape datpoint3
  Set datplane1 = hypFact.AddNewPlaneDatum(absRef)
  HybridBody1.AppendHybridShape datplane1

  hypFact.DeleteObjectForDatum Reference0
  hypFact.DeleteObjectForDatum Reference1
  hypFact.DeleteObjectForDatum Reference2
  hypFact.DeleteObjectForDatum absRef

  Set absdatRef = wPart.CreateReferenceFromGeometry(datplane1)

  UpdatePartErr wPart, wPart.name & "/" & HybridBody1.name
  wPart.InWorkObject = backWork
  Set toolCall23=absdatRef
End Function

Function toolCall24(wpart,body,absref)
  UpdateObjectErr wPart, Body, wPart.name & "/" & Body.name
  Set sketch = Body.Sketches.Add(absRef)
  CATIA.ActiveDocument.Selection.Clear
  CATIA.ActiveDocument.Selection.Add(sketch)
  CATIA.ActiveDocument.Selection.VisProperties.SetShow(1)
  CATIA.ActiveDocument.Selection.Clear

  Set factory2d = sketch.OpenEdition
  Set Axis2D7 = Sketch.AbsoluteAxis
  Set Line2D8 = Axis2D7.HorizontalReference
  Line2D8.ReportName = 1
  Set Line2D9 = Axis2D7.VerticalReference
  Line2D9.ReportName = 2
  Set constraints1 = Sketch.Constraints

  Set startPoint = Factory2D.CreatePoint(-14, 0)
  Set endPoint = Factory2D.CreatePoint(-14, 1.5)
  Set line = factory2d.CreateLine(-14, 0, -14, 1.5)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-14, 1.5)
  Set endPoint = Factory2D.CreatePoint(-13.1339745962156, 0)
  Set line = factory2d.CreateLine(-14, 1.5, -13.1339745962156, 0)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set startPoint = Factory2D.CreatePoint(-13.1339745962156, 0)
  Set endPoint = Factory2D.CreatePoint(-14, 0)
  Set line = factory2d.CreateLine(-13.1339745962156, 0, -14, 0)
  line.StartPoint = startPoint
  line.EndPoint = endPoint
  Set ref1 = wpart.CreateReferenceFromObject(startPoint)
  Set ref2 = wpart.CreateReferenceFromObject(endPoint)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Set pk1 = Factory2D.CreatePoint(-13.1339745962156, 0)
  Set pk2 = Factory2D.CreatePoint(-14, 0)
  Set line = Factory2d.CreateLine(-13.1339745962156, 0, -14, 0)
  sketch.CenterLine = line
  Set ref1 = wpart.CreateReferenceFromObject(pk1)
  Set ref2 = wpart.CreateReferenceFromObject(pk2)
  Set ref3 = wpart.CreateReferenceFromObject(line)
  Set constraint1 = constraints1.AddMonoEltCst(catCstTypeReference, ref1)
  Set constraint1 = constraints1.AddMonoEltCst(catCstTypeReference, ref2)
  Set constraint1 = constraints1.AddMonoEltCst(catCstTypeReference, ref3)

  Sketch.CloseEdition
  UpdateObjectErr wpart, Sketch, wPart.name & "/" & Body.name & "/" & Sketch.name
  Set sketch7 = sketch
  Set toolCall24=sketch7
End Function

Function toolCall25(wpart,HybridBody2)
  set backWork = wPart.InWorkObject 
  UpdateObjectErr wPart, HybridBody2, wPart.name & "/" & HybridBody2.name
  Set hypFact = wPart.HybridShapeFactory
  Set HybridShapePointCoord0 = hypFact.AddNewPointCoord(0, 0, 0)
  HybridShapePointCoord0.Name = "PointOfCoincidenceStart:CP"
  HybridBody2.AppendHybridShape HybridShapePointCoord0
  UpdateObjectErr wPart, HybridShapePointCoord0, wPart.name & "/" & HybridBody2.name & "/" & HybridShapePointCoord0.name
  Set HybridShapePointCoord1 = hypFact.AddNewPointCoord(0, 0, -1)
  HybridShapePointCoord1.Name = "PointOfCoincidenceEnd_X:CP"
  HybridBody2.AppendHybridShape HybridShapePointCoord1
  UpdateObjectErr wPart, HybridShapePointCoord1, wPart.name & "/" & HybridBody2.name & "/" & HybridShapePointCoord1.name
  Set HybridShapePointCoord2 = hypFact.AddNewPointCoord(0, 1, 0)
  HybridShapePointCoord2.Name = "PointOfCoincidenceEnd_Y:CP"
  HybridBody2.AppendHybridShape HybridShapePointCoord2
  UpdateObjectErr wPart, HybridShapePointCoord2, wPart.name & "/" & HybridBody2.name & "/" & HybridShapePointCoord2.name
  Set HybridShapePointCoord3 = hypFact.AddNewPointCoord(1, 0, 0)
  HybridShapePointCoord3.Name = "PointOfCoincidenceEnd_Z:CP"
  HybridBody2.AppendHybridShape HybridShapePointCoord3
  UpdateObjectErr wPart, HybridShapePointCoord3, wPart.name & "/" & HybridBody2.name & "/" & HybridShapePointCoord3.name
  Set Reference0 = wPart.CreateReferenceFromGeometry(HybridShapePointCoord0)
  Set Reference1 = wPart.CreateReferenceFromGeometry(HybridShapePointCoord1)
  Set Reference2 = wPart.CreateReferenceFromGeometry(HybridShapePointCoord2)
  Set Reference3 = wPart.CreateReferenceFromGeometry(HybridShapePointCoord3)
  Set absPlaneOXY = hypFact.AddNewPlane3Points(Reference0, Reference1, Reference2)
  absPlaneOXY.Name = "PlaneOffset:CP"
  HybridBody2.AppendHybridShape absPlaneOXY
  UpdateObjectErr wPart, absPlaneOXY, wPart.name & "/" & HybridBody2.name & "/" & absPlaneOXY.name
  Set absPlaneOXZ = hypFact.AddNewPlane3Points(Reference0, Reference3, Reference1)
  absPlaneOXZ.Name = "PlaneAngular:CP"
  HybridBody2.AppendHybridShape absPlaneOXZ
  UpdateObjectErr wPart, absPlaneOXZ, wPart.name & "/" & HybridBody2.name & "/" & absPlaneOXZ.name
  Set lineOX = hypFact.AddNewLinePtPt(Reference0, Reference1)
  lineOX.Name = "LineCoincidence_X:CP"
  HybridBody2.AppendHybridShape lineOX
  UpdateObjectErr wPart, lineOX, wPart.name & "/" & HybridBody2.name & "/" & lineOX.name
  Set lineOY = hypFact.AddNewLinePtPt(Reference0, Reference2)
  lineOY.Name = "LineCoincidence_Y:CP"
  HybridBody2.AppendHybridShape lineOY
  UpdateObjectErr wPart, lineOY, wPart.name & "/" & HybridBody2.name & "/" & lineOY.name
  Set lineOZ = hypFact.AddNewLinePtPt(Reference0, Reference3)
  lineOZ.Name = "LineCoincidence:CP"
  HybridBody2.AppendHybridShape lineOZ
  UpdateObjectErr wPart, lineOZ, wPart.name & "/" & HybridBody2.name & "/" & lineOZ.name
  Set absRef = wPart.CreateReferenceFromGeometry(absPlaneOXY)
  UpdatePartErr wPart, wPart.name & "/" & HybridBody2.Name
  wPart.InWorkObject = backWork
  Set toolCall25=absref
End Function

Sub CreatePart1
  On Error Resume Next

  Set SaveCaseDoc = CATIA.Documents.Item("GEAB2_0_30_15_B_13_b.CATPart")

  If (Err.Number <> 0) Then
    ucaseName = GetUCaseName("GEAB2_0_30_15_B_13_b.CATPart")
    Set SaveCaseDoc = CATIA.Documents.Item(ucaseName)
  End If

  Set PartDocument = SaveCaseDoc

  If (IsObject(PartDocument)) Then
    PartDocument.Activate
    Exit Sub
  End If

  Set fso = CreateObject("Scripting.FileSystemObject")

  If (fso.FileExists(storePath & "GEAB2_0_30_15_B_13_b.CATPart")) Then
    CATIA.Documents.Open(storePath & "GEAB2_0_30_15_B_13_b.CATPart")
    Set fso = Nothing
    Exit Sub
  ElseIf (fso.FileExists(storePath & GetUCaseName("GEAB2_0_30_15_B_13_b.CATPart"))) Then
    CATIA.Documents.Open(storePath & GetUCaseName("GEAB2_0_30_15_B_13_b.CATPart"))
    Set fso = Nothing
    Exit Sub
  End If

  Set fso = Nothing

  On Error Goto 0

  Set PartDocument = CATIA.Documents.Add("Part")
  Set unused1 = Partdocument.Product.UserRefProperties.CreateString("NB", "GEAB2.0-30-15-B-13_b")
  Set unused1 = Partdocument.Product.UserRefProperties.CreateString("NN", "GEAHB, GEAHBB, GEAHBG, GEAHS, GEAB, GEABB, GEABG, GEAS, GEAKB, GEAKBB, GEAKBG, GEAKS_2.0_body")
  Set unused1 = Partdocument.Product.UserRefProperties.CreateString("NT", "Spur Gears - Pressure Angle 20 degree Module 2.0")
  Set unused1 = Partdocument.Product.UserRefProperties.CreateString("NBSYN", "$PN._b")
  Set unused1 = Partdocument.Product.UserRefProperties.CreateString("LINA", "GEAB2.0-30-15-B-13")
  Set unused1 = Partdocument.Product.UserRefProperties.CreateString("CATALOG", "Misumi")
  Set unused1 = Partdocument.Product.UserRefProperties.CreateString("PN", "GEAB2.0-30-15-B-13")
  Set unused1 = Partdocument.Product.UserRefProperties.CreateString("SHS", "Round Hole+Tap")
  Set unused1 = Partdocument.Product.UserRefProperties.CreateString("MAT", "S45C Equivalent")
  Set unused1 = Partdocument.Product.UserRefProperties.CreateString("ST", "-")
  Set unused1 = Partdocument.Product.UserRefProperties.CreateString("MOD", "2.0")
  Set unused1 = Partdocument.Product.UserRefProperties.CreateString("NT", "30")
  Set unused1 = Partdocument.Product.UserRefProperties.CreateString("B", "15")
  Set unused1 = Partdocument.Product.UserRefProperties.CreateString("TS", "B")
  Set unused1 = Partdocument.Product.UserRefProperties.CreateString("PS", "13")
  Set unused1 = Partdocument.Product.UserRefProperties.CreateString("DD", "60")
  Set unused1 = Partdocument.Product.UserRefProperties.CreateString("D", "64")
  Set unused1 = Partdocument.Product.UserRefProperties.CreateString("G", "55")
  Set unused1 = Partdocument.Product.UserRefProperties.CreateString("H", "48")
  Set unused1 = Partdocument.Product.UserRefProperties.CreateString("L", "29")
  Set unused1 = Partdocument.Product.UserRefProperties.CreateString("LL1", "14")
  Set unused1 = Partdocument.Product.UserRefProperties.CreateString("LL2", "7")
  Set unused1 = Partdocument.Product.UserRefProperties.CreateString("M", "M6")
  Set unused1 = Partdocument.Product.UserRefProperties.CreateString("ALT1", "w/o Set Screw")
  Set unused1 = Partdocument.Product.UserRefProperties.CreateString("ALT2", "w/o TPC (Tapped Hole Dimension)")
  Set unused1 = Partdocument.Product.UserRefProperties.CreateString("TPC", "N/A")
  Set unused1 = Partdocument.Product.UserRefProperties.CreateString("ALT11", "w/o GBA (Gear bottom adjustment of phase focus)")
  Set unused1 = Partdocument.Product.UserRefProperties.CreateString("ALT10", "w/o BS (Boss Cut)")
  Set unused1 = Partdocument.Product.UserRefProperties.CreateString("BS", "0.0")
  Set unused1 = Partdocument.Product.UserRefProperties.CreateString("ALT4", "N/A")
  Set unused1 = Partdocument.Product.UserRefProperties.CreateString("Z", "0")
  Set unused1 = Partdocument.Product.UserRefProperties.CreateString("J", "0.0")
  Set unused1 = Partdocument.Product.UserRefProperties.CreateString("ALT5", "N/A")
  Set unused1 = Partdocument.Product.UserRefProperties.CreateString("Q", "0")
  Set unused1 = Partdocument.Product.UserRefProperties.CreateString("R", "0")
  Set unused1 = Partdocument.Product.UserRefProperties.CreateString("S", "0")
  Set unused1 = Partdocument.Product.UserRefProperties.CreateString("T", "0")
  Set unused1 = Partdocument.Product.UserRefProperties.CreateString("ALT9", "Not applicable")
  Set unused1 = Partdocument.Product.UserRefProperties.CreateString("SRG", "0.0")
  Set unused1 = Partdocument.Product.UserRefProperties.CreateString("DD2", "0.0")
  Set unused1 = Partdocument.Product.UserRefProperties.CreateString("MM", "0.00")
  Set unused1 = Partdocument.Product.UserRefProperties.CreateString("NN", "0.00")
  Set unused1 = Partdocument.Product.UserRefProperties.CreateString("ALT6", "N/A")
  Set unused1 = Partdocument.Product.UserRefProperties.CreateString("LFC", "0")
  Set unused1 = Partdocument.Product.UserRefProperties.CreateString("LTC", "0")
  Set unused1 = Partdocument.Product.UserRefProperties.CreateString("MALT6", "N/A")
  Set unused1 = Partdocument.Product.UserRefProperties.CreateString("C", "0.0")
  Set unused1 = Partdocument.Product.UserRefProperties.CreateString("ALT7", "w/o Side Through Hole")
  Set unused1 = Partdocument.Product.UserRefProperties.CreateString("KFC", "0")
  Set unused1 = Partdocument.Product.UserRefProperties.CreateString("KTC", "0")
  Set unused1 = Partdocument.Product.UserRefProperties.CreateString("K", "0.0")
  Set unused1 = Partdocument.Product.UserRefProperties.CreateString("ALT3", "w/o Side Tapped Hole")
  Set unused1 = Partdocument.Product.UserRefProperties.CreateString("DIRALT3", "N/A")
  Set unused1 = Partdocument.Product.UserRefProperties.CreateString("QFC", "0")
  Set unused1 = Partdocument.Product.UserRefProperties.CreateString("QTC", "0")
  Set unused1 = Partdocument.Product.UserRefProperties.CreateString("MALT3", "N/A")
  Set unused1 = Partdocument.Product.UserRefProperties.CreateString("ALT8", "w/o Side Counterbored")
  Set unused1 = Partdocument.Product.UserRefProperties.CreateString("DIRALT8", "N/A")
  Set unused1 = Partdocument.Product.UserRefProperties.CreateString("ZFC", "0")
  Set unused1 = Partdocument.Product.UserRefProperties.CreateString("ZTC", "0")
  Set unused1 = Partdocument.Product.UserRefProperties.CreateString("U", "0")
  Set unused1 = Partdocument.Product.UserRefProperties.CreateString("U1", "0.0")
  Set unused1 = Partdocument.Product.UserRefProperties.CreateString("U2", "0.0")
  Set unused1 = Partdocument.Product.UserRefProperties.CreateString("F", "0.0")
  Set unused1 = Partdocument.Product.UserRefProperties.CreateString("VENDOR", "MISUMI")
  Set unused1 = Partdocument.Product.UserRefProperties.CreateString("SUPPLIER", "MISUMI")
  Set unused1 = Partdocument.Product.UserRefProperties.CreateString("ARTICLENO", "GEAB2.0-30-15-B-13_b")
  Set unused1 = Partdocument.Product.UserRefProperties.CreateString("BOMINFO", "GEAB2.0-30-15-B-13")
  Set unused1 = Partdocument.Product.UserRefProperties.CreateString("CREATOR", "CADENAS GmbH")
  Partdocument.Product.PartNumber = "GEAB2.0-30-15-B-13_b"
  Partdocument.Product.Definition = "Cadenas PARTsolutions"
  Partdocument.Product.DescriptionRef = "Spur Gears - Pressure Angle 20 degree Module 2.0"
  Set mident = Partdocument.Product.UserRefProperties.CreateString("PSOL_MIDENT", "{$CADENAS_DATA/23d-libs/misumi/metric/54_spur_gears/geab20/geab20.prj},489 {VTYP=3D},{NB=GEAB2.0-30-15-B-13_b},{LINA=GEAB2.0-30-15-B-13},{NN=GEAHB, GEAHBB, GEAHBG, GEAHS, GEAB, GEABB, GEABG, GEAS, GEAKB, GEAKBB, GEAKBG, GEAKS_2.0_body},{DATE=11.10.2021 04:24:21},{GEOMDATE=28.09.2021 08:41:24},{VERSION=},{LINEID=10},{WBVAR=SHS,MAT,ST,NT,B,TS,PS,ALT1,ALT2,TPC,ALT11,ALT10,BS,ALT4,Z,J,ALT5,Q,R,S,T,ALT9,SRG,ALT6,LFC,LTC,MALT6,ALT7,KFC,KTC,K,ALT3,DIRALT3,QFC,QTC,MALT3,ALT8,DIRALT8,ZFC,ZTC,U},{WBNUMERIC=NT,B,BS,Z,J,Q,R,S,T,SRG,LFC,LTC,KFC,KTC,K,QFC,QTC,ZFC,ZTC,U}  {NB=GEAB2.0-30-15-B-13_b},{LINA=GEAB2.0-30-15-B-13},{KT=DUMMY},{PN=GEAB2.0-30-15-B-13},{TYPE=GEAB},{SHSALG= 'RH','Round Hole','RHT','Round Hole+Tap','KGH','Key Groove Hole','KGHT','Key Groove Hole+Tap' },{SHALG=1},{MATALG= 'S45C', 'S45C Equivalent', 'SUS304', 'SUS304' },{SHS=RHT},{MAT=S45C},{ST=},{STALG= '','-','BO','Black Oxide','ENP','Electroless Nickel Plating'},{MOD=2.0},{NT=30},{NTA=12,13,14,15,16,17,18,19,20,21,22,23,24,25,26,27,28,29,30,32,33,34,35,36,38,39,40,42,44,45,46,48,49,50,51,52,54,55,56,57,58,60,62,63,64,65,66,68,69,70,72,75,76,77,78,80,81,84,85,88,90,91,92,95,96,98,99,100},{B=15},{TS=B},{TSALG='B','B'},{TSPN=-B},{PS=13},{PSALG='8','8','9','9','10','10','11','11','12','12','13','13','14','14','15','15','16','16','17','17','18','18','19','19','20','20','21','21','22','22','23','23','24','24','25','25','26','26','27','27','28','28','29','29','30','30','31','31','32','32','33','33','34','34','35','35','36','36'},{PS1='8','8','9','9','10','10','11','11','12','12','13','13','14','14','15','15','16','16','17','17','18','18','19','19','20','20','21','21','22','22','23','23','24','24','25','25','26','26','27','27','28','28','29','29','30','30','31','31','32','32','33','33','34','34','35','35','36','36'},{PS2='8N','8N','10N','10N','10K','10K','11N','11N','12N','12N','13N','13N','14N','14N','15N','15N','16N','16N','17N','17N','18N','18N','19N','19N','20N','20N','21N','21N','22N','22N','23N','23N','24N','24N','25N','25N','26N','26N','27N','27N','28N','28N','29N','29N','30N','30N','31N','31N','32N','32N'},{P=13.00},{P2=13},{DD=60},{D=64},{G=55},{H=48},{L=29},{LL1=14},{LL2=7},{M=M6},{M2=6},{M3=6},{ML=17.5},{BB=5},{TT=0},{ALT1=},{ALT1ALG='', 'w/o Set Screw', 'KC90','with KC90 (Set Screw)','KC120','with KC120 (Set Screw)' },{ALT1PN=},{KC=0},{ALT2=},{ALT2ALG= '','w/o TPC (Tapped Hole Dimension)','TPC','with TPC (Tapped Hole Dimension)' },{TPC=N/A},{TPCALG= 'N/A' },{ALT2PN=},{TPC3D=0},{ALT11=},{ALT11ALG= '', 'w/o GBA (Gear bottom adjustment of phase focus)','GBA','with GBA (Gear bottom adjustment of phase focus)' },{ALT11PN=},{DEG=0},{ALT10=},{ALT10ALG= '','w/o BS (Boss Cut)','BS','with BS (Boss Cut)' },{BS=0.0},{BSALG=0},{BSMIN=9},{BSMAX=14},{LL13D=14.000},{ALT10PN=},{LL23D=22.000},{LBS=29.000},{ALT4=},{ALT4ALG= '','N/A' },{ALT41=0},{ALT42=0},{ALT4PN=},{Z=0},{ZALG=0},{ZMINL=15},{ZMAXL=51},{ZMINR=15},{ZMAXR=44},{ZPN=},{J=0.0},{JALG=0},{JMIN=2},{JMAX=0},{JPN=},{ALT5=},{ALT5ALG= '','N/A' },{ALT5PN=},{Q=0},{QALG=0},{QMIN=15},{QMAX=44},{QPN=},{R=0},{RALG=0},{RMIN=15},{RMAX=44},{RPN=},{S=0},{SALG=0},{SMIN=3},{SMAX=23},{SPN=},{T=0},{TALG=0},{TMIN=3},{TMAX=0},{TPN=},{ALT9=},{ALT9ALG= '','Not applicable' },{SRG=0.0},{SRGALG=0},{SRGMIN=3.5},{SRGMINALG=3.500},{SRGMAX=0},{SRGMAXALG=0.000},{DD2=0.0},{MM=0.00},{NN=0.00},{DD2ALG=0.000},{MMALG=0.000},{NNALG=0.000},{ALT9PN=},{ALT6=},{ALT6ALG= '','N/A' },{LFC=0},{LFCALG=0},{LTC=0},{LTCALG=0},{LPCDMIN=21.000},{LPCDMAX=47.000},{MALT6=N/A},{MALT6ALG= 'N/A' },{C=0.0},{ALT6PN=},{ALT7=},{ALT7ALG= '','w/o Side Through Hole','KFC','with KFC (Side Through Hole)','KTC','with KTC (Side Through Hole)' },{ALT7PN=},{KFC=0},{KFCALG=[0]},{KTC=0},{KTCALG=[0]},{KPCDMIN1=20},{KPCDMAX1=41},{KPCDMIN2=55.000},{KPCDMAX2=48.000},{KPCD=0},{K=0.0},{KALG=[0]},{KALT7L=15},{TIF=2},{SCREW=6},{SCREWL=16},{PLANE=24},{PLANE1=24},{ALT3=},{ALT3ALG= '','w/o Side Tapped Hole','QFC','with QFC (Side Tapped Hole)','QTC','with QTC (Side Tapped Hole)' },{ALT3PN=},{DIRALT3=},{DIRALT3ALG= '','N/A' },{QFC=0},{QFCALG=[0]},{QTC=0},{QTCALG=[0]},{QPCDMIN1=20},{QPCDMAX1=41},{QPCDMIN2=55},{QPCDMAX2=48},{CIFMALT3=3},{QPCD=0},{MALT3=N/A},{MALT3ALG= 'N/A' },{MALT3L=0},{MS1=3},{PITCH=0},{ALT8=},{ALT8ALG= '','w/o Side Counterbored','ZFC','with ZFC (4 Places Side Counterbored)','ZTC','with ZTC (3 Places Side Counterbored)' },{ALT8PN=},{DIRALT8=},{DIRALT8ALG= '','N/A' },{ZFC=0},{ZFCALG=[0]},{ZTC=0},{ZTCALG=[0]},{ZPCDMIN1=23},{ZPCDMIN2=59},{ZPCDMAX1=37},{ZPCDMAX2=44},{ZPCD=0},{U=0},{UALG=[0]},{UMAX=0},{UMAX1=0},{UMAX2=6},{UMIN=3},{U1=0.0},{U2=0.0},{F=0.0},{PCD=0},{SHN=0},{SHDEG1=0},{SHDEG2=0},{PZQRDD2=13},{ALT3LBS=28.5},{MOD3D=2},{D1=3},{D2=6},{D3=20},{D4=0.2},{D5=10},{D6=12},{D7=1.7},{D8=1},{D9=1.641818},{S1=15},{S2=2}")

  set wpart=partDocument.Part
  Dim skCoord(8)
  Dim Body
  Set Body = wPart.MainBody
  Body.Name="GEAB2.0-30-15-B-13_b"

  Dim HybridBody1
  Set HybridBody1 = wPart.HybridBodies.Add
  HybridBody1.Name="GEAB2.0-30-15-B-13_b Geo"

  CATIA.ActiveDocument.Selection.Clear
  CATIA.ActiveDocument.Selection.Add(wPart.OriginElements.PlaneXY )
  CATIA.ActiveDocument.Selection.Add(wPart.OriginElements.PlaneYZ )
  CATIA.ActiveDocument.Selection.Add(wPart.OriginElements.PlaneZX )
  CATIA.ActiveDocument.Selection.Add(HybridBody1)
  CATIA.ActiveDocument.Selection.VisProperties.SetShow(1)
  CATIA.ActiveDocument.Selection.Clear

  Set absref=toolCall0(wpart,HybridBody1)
  Set sketch4=toolCall1(wpart,body,absref)
  UpdateObjectErr wPart, Body, wPart.name & "/" & Body.Name
  Set shaft = wPart.ShapeFactory.AddNewShaft(sketch4)
  shaft.firstAngle.value = 0
  shaft.SecondAngle.value = 360
  UpdatePartErr wPart, wPart.name & "/" & Body.name & "/" & shaft.name
  Set absref=toolCall2(wpart,HybridBody1)
  Set sketch6=toolCall3(wpart,body,absref)
  UpdateObjectErr wPart, Body, wPart.name & "/" & Body.Name
  Set pocket = wPart.ShapeFactory.AddNewPocket(sketch6, 16)
  pocket.IsSymmetric = True
  UpdatePartErr wPart, wPart.name & "/" & Body.name & "/" & pocket.name
  Set absref=toolCall4(wpart,HybridBody1)
  Set sketch8=toolCall5(wpart,body,absref)
  UpdateObjectErr wPart, Body, wPart.name & "/" & Body.Name
  Set groove = wPart.ShapeFactory.AddNewGroove(sketch8)
  groove.FirstAngle.Value = 0
  groove.SecondAngle.Value = 360
  UpdatePartErr wPart, wPart.name & "/" & Body.name & "/" & groove.name
  Set absref=toolCall6(wpart,HybridBody1)
  Set sketch10=toolCall7(wpart,body,absref)
  UpdateObjectErr wPart, Body, wPart.name & "/" & Body.Name
  Set groove = wPart.ShapeFactory.AddNewGroove(sketch10)
  groove.FirstAngle.Value = 0
  groove.SecondAngle.Value = 360
  UpdatePartErr wPart, wPart.name & "/" & Body.name & "/" & groove.name
  Set absref=toolCall8(wpart,HybridBody1)
  Set sketch12=toolCall9(wpart,body,absref)
  UpdateObjectErr wPart, Body, wPart.name & "/" & Body.Name
  Set groove = wPart.ShapeFactory.AddNewGroove(sketch12)
  groove.FirstAngle.Value = 0
  groove.SecondAngle.Value = 360
  UpdatePartErr wPart, wPart.name & "/" & Body.name & "/" & groove.name
  Set absref=toolCall10(wpart,HybridBody1)
  Set sketch17=toolCall11(wpart,body,absref)
  UpdateObjectErr wPart, Body, wPart.name & "/" & Body.Name
  Set groove = wPart.ShapeFactory.AddNewGroove(sketch17)
  groove.FirstAngle.Value = 0
  groove.SecondAngle.Value = 360
  UpdatePartErr wPart, wPart.name & "/" & Body.name & "/" & groove.name
  Set thread18=toolCall12(partdocument,wpart,body,HybridBody1)
  Dim bodycurrrent
  Set bodycurrrent = Body

  Dim HybridBody2
  Set HybridBody2 = wPart.HybridBodies.Add
  HybridBody2.Name="ConnectionBody"

  CATIA.ActiveDocument.Selection.Clear
  CATIA.ActiveDocument.Selection.Add(HybridBody2)
  CATIA.ActiveDocument.Selection.VisProperties.SetShow(1)
  CATIA.ActiveDocument.Selection.Clear

  Set absref=toolCall14(wpart,HybridBody2)
  Set absref=toolCall15(wpart,HybridBody2)
  Set absref=toolCall16(wpart,HybridBody2)
  CATIA.ActiveDocument.selection.clear
  CATIA.ActiveDocument.selection.add(body)
  CATIA.ActiveDocument.selection.VisProperties.SetRealColor 176, 176, 176,1
  CATIA.ActiveDocument.selection.VisProperties.SetRealOpacity 255,1


  wPart.InWorkObject = Body
  ProcessDocumentBeforeSave PartDocument, "GEAB2_0_30_15_B_13_b.CATPart"
  wpart.Update
  SaveDocument PartDocument, "GEAB2_0_30_15_B_13_b.CATPart"
End Sub


Sub CreatePart2
  On Error Resume Next

  Set SaveCaseDoc = CATIA.Documents.Item("SET_SCREW6_16.CATPart")

  If (Err.Number <> 0) Then
    ucaseName = GetUCaseName("SET_SCREW6_16.CATPart")
    Set SaveCaseDoc = CATIA.Documents.Item(ucaseName)
  End If

  Set PartDocument = SaveCaseDoc

  If (IsObject(PartDocument)) Then
    PartDocument.Activate
    Exit Sub
  End If

  Set fso = CreateObject("Scripting.FileSystemObject")

  If (fso.FileExists(storePath & "SET_SCREW6_16.CATPart")) Then
    CATIA.Documents.Open(storePath & "SET_SCREW6_16.CATPart")
    Set fso = Nothing
    Exit Sub
  ElseIf (fso.FileExists(storePath & GetUCaseName("SET_SCREW6_16.CATPart"))) Then
    CATIA.Documents.Open(storePath & GetUCaseName("SET_SCREW6_16.CATPart"))
    Set fso = Nothing
    Exit Sub
  End If

  Set fso = Nothing

  On Error Goto 0

  Set PartDocument = CATIA.Documents.Add("Part")
  Set unused1 = Partdocument.Product.UserRefProperties.CreateString("NB", "SET-SCREW6-16")
  Set unused1 = Partdocument.Product.UserRefProperties.CreateString("NN", "SET-SCREW")
  Set unused1 = Partdocument.Product.UserRefProperties.CreateString("NT", "Set Screw - Flat End")
  Set unused1 = Partdocument.Product.UserRefProperties.CreateString("NBSYN", "$PN.")
  Set unused1 = Partdocument.Product.UserRefProperties.CreateString("LINA", "SET-SCREW6-16")
  Set unused1 = Partdocument.Product.UserRefProperties.CreateString("CATALOG", "Misumi")
  Set unused1 = Partdocument.Product.UserRefProperties.CreateString("PN", "SET-SCREW6-16")
  Set unused1 = Partdocument.Product.UserRefProperties.CreateString("M", "6.0")
  Set unused1 = Partdocument.Product.UserRefProperties.CreateString("P", "1.00")
  Set unused1 = Partdocument.Product.UserRefProperties.CreateString("L", "16")
  Set unused1 = Partdocument.Product.UserRefProperties.CreateString("B", "3.0")
  Set unused1 = Partdocument.Product.UserRefProperties.CreateString("C", "2.0")
  Set unused1 = Partdocument.Product.UserRefProperties.CreateString("DD", "4.0")
  Set unused1 = Partdocument.Product.UserRefProperties.CreateString("VENDOR", "MISUMI")
  Set unused1 = Partdocument.Product.UserRefProperties.CreateString("SUPPLIER", "MISUMI")
  Set unused1 = Partdocument.Product.UserRefProperties.CreateString("ARTICLENO", "SET-SCREW6-16")
  Set unused1 = Partdocument.Product.UserRefProperties.CreateString("BOMINFO", "SET-SCREW6-16")
  Set unused1 = Partdocument.Product.UserRefProperties.CreateString("CREATOR", "CADENAS GmbH")
  Partdocument.Product.PartNumber = "SET-SCREW6-16"
  Partdocument.Product.Definition = "Cadenas PARTsolutions"
  Partdocument.Product.DescriptionRef = "Set Screw - Flat End"
  Set mident = Partdocument.Product.UserRefProperties.CreateString("PSOL_MIDENT", "{$CADENAS_DATA/23d-libs/misumi/metric/accessories/set_screw.prj},171 {VTYP=3D},{NB=SET-SCREW6-16},{LINA=SET-SCREW6-16},{NN=SET-SCREW},{DATE=30.06.2021 13:30:10},{GEOMDATE=11.12.2013 00:00:00},{VERSION=},{LINEID=70},{WBVAR=L},{WBNUMERIC=L}  {NB=SET-SCREW6-16},{LINA=SET-SCREW6-16},{KT=DUMMY},{PN=SET-SCREW6-16},{TYPE=SET-SCREW},{M=6.0},{P=1.00},{L=16},{LMIN=2.9},{LALG=[2.9:42/0.1]},{B=3.0},{C=2.0},{DD=4.0}")

  set wpart=partDocument.Part
  Dim skCoord(8)
  Dim Body
  Set Body = wPart.MainBody
  Body.Name="SET-SCREW6-16"

  Dim HybridBody1
  Set HybridBody1 = wPart.HybridBodies.Add
  HybridBody1.Name="SET-SCREW6-16 Geo"

  CATIA.ActiveDocument.Selection.Clear
  CATIA.ActiveDocument.Selection.Add(wPart.OriginElements.PlaneXY )
  CATIA.ActiveDocument.Selection.Add(wPart.OriginElements.PlaneYZ )
  CATIA.ActiveDocument.Selection.Add(wPart.OriginElements.PlaneZX )
  CATIA.ActiveDocument.Selection.Add(HybridBody1)
  CATIA.ActiveDocument.Selection.VisProperties.SetShow(1)
  CATIA.ActiveDocument.Selection.Clear

  Set absref=toolCall17(wpart,HybridBody1)
  Set sketch3=toolCall18(wpart,body,absref)
  UpdateObjectErr wPart, Body, wPart.name & "/" & Body.Name
  Set shaft = wPart.ShapeFactory.AddNewShaft(sketch3)
  shaft.firstAngle.value = 0
  shaft.SecondAngle.value = 360
  UpdatePartErr wPart, wPart.name & "/" & Body.name & "/" & shaft.name
  Set thread4=toolCall19(partdocument,wpart,body,HybridBody1)
  Set absref=toolCall21(wpart,HybridBody1)
  Set sketch5=toolCall22(wpart,body,absref)
  UpdateObjectErr wPart, Body, wPart.name & "/" & Body.Name
  Set pocket = wPart.ShapeFactory.AddNewPocket(sketch5, 2)
  pocket.DirectionOrientation = 1
  UpdatePartErr wPart, wPart.name & "/" & Body.name & "/" & pocket.name
  Set absref=toolCall23(wpart,HybridBody1)
  Set sketch7=toolCall24(wpart,body,absref)
  UpdateObjectErr wPart, Body, wPart.name & "/" & Body.Name
  Set groove = wPart.ShapeFactory.AddNewGroove(sketch7)
  groove.FirstAngle.Value = 0
  groove.SecondAngle.Value = 360
  UpdatePartErr wPart, wPart.name & "/" & Body.name & "/" & groove.name
  Dim bodycurrrent
  Set bodycurrrent = Body

  Dim HybridBody2
  Set HybridBody2 = wPart.HybridBodies.Add
  HybridBody2.Name="ConnectionBody"

  CATIA.ActiveDocument.Selection.Clear
  CATIA.ActiveDocument.Selection.Add(HybridBody2)
  CATIA.ActiveDocument.Selection.VisProperties.SetShow(1)
  CATIA.ActiveDocument.Selection.Clear

  Set absref=toolCall25(wpart,HybridBody2)
  CATIA.ActiveDocument.selection.clear
  CATIA.ActiveDocument.selection.add(body)
  CATIA.ActiveDocument.selection.VisProperties.SetRealColor 176, 176, 176,1
  CATIA.ActiveDocument.selection.VisProperties.SetRealOpacity 255,1


  wPart.InWorkObject = Body
  ProcessDocumentBeforeSave PartDocument, "SET_SCREW6_16.CATPart"
  wpart.Update
  SaveDocument PartDocument, "SET_SCREW6_16.CATPart"
End Sub


' Create Assembly
Sub CreateAsm2
  On Error Resume Next

  Set SaveCaseDoc = CATIA.Documents.Item("GEAB2_0_30_15_B_13.CATProduct")

  If (Err.Number <> 0) Then
    ucaseName = GetUCaseName("GEAB2_0_30_15_B_13.CATProduct")
    Set SaveCaseDoc = CATIA.Documents.Item(ucaseName)
  End If

  Set PartDocument = SaveCaseDoc

  If (IsObject(PartDocument)) Then
    PartDocument.Activate
    Exit Sub
  End If

  Set fso = CreateObject("Scripting.FileSystemObject")

  If (fso.FileExists(storePath & "GEAB2_0_30_15_B_13.CATProduct")) Then
    CATIA.Documents.Open(storePath & "GEAB2_0_30_15_B_13.CATProduct")
    Set fso = Nothing
    Exit Sub
  ElseIf (fso.FileExists(storePath & GetUCaseName("GEAB2_0_30_15_B_13.CATProduct"))) Then
    CATIA.Documents.Open(storePath & GetUCaseName("GEAB2_0_30_15_B_13.CATProduct"))
    Set fso = Nothing
    Exit Sub
  End If

  Set fso = Nothing

  On Error Goto 0

  Dim mat(11)
  Dim pin(0)
  Dim docName As String
  Set ProductDocument = CATIA.Documents.Add("Product")
  Dim Product
  Set Product = ProductDocument.Product

  Set unused1 = Product.UserRefProperties.CreateString("NB", "GEAB2.0-30-15-B-13")
  Set unused1 = Product.UserRefProperties.CreateString("NN", "GEAHB, GEAHBB, GEAHBG, GEAHS, GEAB, GEABB, GEABG, GEAS, GEAKB, GEAKBB, GEAKBG, GEAKS_2.0")
  Set unused1 = Product.UserRefProperties.CreateString("NT", "Spur Gears - Pressure Angle 20 degree Module 2.0")
  Set unused1 = Product.UserRefProperties.CreateString("NBSYN", "$PN.")
  Set unused1 = Product.UserRefProperties.CreateString("LINA", "GEAB2.0-30-15-B-13")
  Set unused1 = Product.UserRefProperties.CreateString("CATALOG", "Misumi")
  Set unused1 = Product.UserRefProperties.CreateString("PN", "GEAB2.0-30-15-B-13")
  Set unused1 = Product.UserRefProperties.CreateString("SHS", "Round Hole+Tap")
  Set unused1 = Product.UserRefProperties.CreateString("MAT", "S45C Equivalent")
  Set unused1 = Product.UserRefProperties.CreateString("ST", "-")
  Set unused1 = Product.UserRefProperties.CreateString("MOD", "2.0")
  Set unused1 = Product.UserRefProperties.CreateString("NT", "30")
  Set unused1 = Product.UserRefProperties.CreateString("B", "15")
  Set unused1 = Product.UserRefProperties.CreateString("TS", "width")
  Set unused1 = Product.UserRefProperties.CreateString("PS", "13")
  Set unused1 = Product.UserRefProperties.CreateString("DD", "60")
  Set unused1 = Product.UserRefProperties.CreateString("D", "64")
  Set unused1 = Product.UserRefProperties.CreateString("G", "55")
  Set unused1 = Product.UserRefProperties.CreateString("H", "48")
  Set unused1 = Product.UserRefProperties.CreateString("L", "29")
  Set unused1 = Product.UserRefProperties.CreateString("LL1", "14")
  Set unused1 = Product.UserRefProperties.CreateString("LL2", "7")
  Set unused1 = Product.UserRefProperties.CreateString("M", "M6")
  Set unused1 = Product.UserRefProperties.CreateString("ALT1", "w/o Set Screw")
  Set unused1 = Product.UserRefProperties.CreateString("ALT2", "w/o TPC (Tapped Hole Dimension)")
  Set unused1 = Product.UserRefProperties.CreateString("TPC", "N/A")
  Set unused1 = Product.UserRefProperties.CreateString("ALT11", "w/o GBA (Gear bottom adjustment of phase focus)")
  Set unused1 = Product.UserRefProperties.CreateString("ALT10", "w/o BS (Boss Cut)")
  Set unused1 = Product.UserRefProperties.CreateString("BS", "0")
  Set unused1 = Product.UserRefProperties.CreateString("ALT4", "N/A")
  Set unused1 = Product.UserRefProperties.CreateString("Z", "0")
  Set unused1 = Product.UserRefProperties.CreateString("J", "0.0")
  Set unused1 = Product.UserRefProperties.CreateString("ALT5", "N/A")
  Set unused1 = Product.UserRefProperties.CreateString("Q", "0")
  Set unused1 = Product.UserRefProperties.CreateString("R", "0")
  Set unused1 = Product.UserRefProperties.CreateString("S", "0")
  Set unused1 = Product.UserRefProperties.CreateString("T", "0")
  Set unused1 = Product.UserRefProperties.CreateString("ALT9", "Not applicable")
  Set unused1 = Product.UserRefProperties.CreateString("SRG", "0.0")
  Set unused1 = Product.UserRefProperties.CreateString("DD2", "0.0")
  Set unused1 = Product.UserRefProperties.CreateString("MM", "0.00")
  Set unused1 = Product.UserRefProperties.CreateString("NN", "0.00")
  Set unused1 = Product.UserRefProperties.CreateString("ALT6", "N/A")
  Set unused1 = Product.UserRefProperties.CreateString("LFC", "0")
  Set unused1 = Product.UserRefProperties.CreateString("LTC", "0")
  Set unused1 = Product.UserRefProperties.CreateString("MALT6", "N/A")
  Set unused1 = Product.UserRefProperties.CreateString("C", "0.0")
  Set unused1 = Product.UserRefProperties.CreateString("ALT7", "w/o Side Through Hole")
  Set unused1 = Product.UserRefProperties.CreateString("KFC", "0")
  Set unused1 = Product.UserRefProperties.CreateString("KTC", "0")
  Set unused1 = Product.UserRefProperties.CreateString("K", "0.0")
  Set unused1 = Product.UserRefProperties.CreateString("ALT3", "w/o Side Tapped Hole")
  Set unused1 = Product.UserRefProperties.CreateString("DIRALT3", "N/A")
  Set unused1 = Product.UserRefProperties.CreateString("QFC", "0")
  Set unused1 = Product.UserRefProperties.CreateString("QTC", "0")
  Set unused1 = Product.UserRefProperties.CreateString("MALT3", "N/A")
  Set unused1 = Product.UserRefProperties.CreateString("ALT8", "w/o Side Counterbored")
  Set unused1 = Product.UserRefProperties.CreateString("DIRALT8", "N/A")
  Set unused1 = Product.UserRefProperties.CreateString("ZFC", "0")
  Set unused1 = Product.UserRefProperties.CreateString("ZTC", "0")
  Set unused1 = Product.UserRefProperties.CreateString("U", "0")
  Set unused1 = Product.UserRefProperties.CreateString("U1", "0.0")
  Set unused1 = Product.UserRefProperties.CreateString("U2", "0.0")
  Set unused1 = Product.UserRefProperties.CreateString("F", "0.0")
  Set unused1 = Product.UserRefProperties.CreateString("VENDOR", "MISUMI")
  Set unused1 = Product.UserRefProperties.CreateString("SUPPLIER", "MISUMI")
  Set unused1 = Product.UserRefProperties.CreateString("ARTICLENO", "GEAB2.0-30-15-B-13")
  Set unused1 = Product.UserRefProperties.CreateString("BOMINFO", "GEAB2.0-30-15-B-13")
  Set unused1 = Product.UserRefProperties.CreateString("CREATOR", "CADENAS GmbH")
  Product.PartNumber = "GEAB2.0-30-15-B-13"
  Product.Definition = "Cadenas PARTsolutions"
  Product.DescriptionRef = "Spur Gears - Pressure Angle 20 degree Module 2.0"
  Set mident = Product.UserRefProperties.CreateString("PSOL_MIDENT", "{$CADENAS_DATA/23d-libs/misumi/metric/54_spur_gears/geab20_asmtab.prj},496 {VTYP=3D},{STYP=ASSTAB},{NB=GEAB2.0-30-15-B-13},{LINA=GEAB2.0-30-15-B-13},{NN=GEAHB, GEAHBB, GEAHBG, GEAHS, GEAB, GEABB, GEABG, GEAS, GEAKB, GEAKBB, GEAKBG, GEAKS_2.0},{DATE=11.10.2021 04:27:36},{GEOMDATE=28.09.2021 09:34:18},{VERSION=},{LINEID=10},{WBVAR=SHS,MAT,ST,NT,B,TS,PS,ALT1,ALT2,TPC,ALT11,ALT10,BS,ALT4,Z,J,ALT5,Q,R,S,T,ALT9,SRG,ALT6,LFC,LTC,MALT6,ALT7,KFC,KTC,K,ALT3,DIRALT3,QFC,QTC,MALT3,ALT8,DIRALT8,ZFC,ZTC,U},{WBNUMERIC=NT,B,BS,Z,J,Q,R,S,T,SRG,LFC,LTC,KFC,KTC,K,QFC,QTC,ZFC,ZTC,U}  {NB=GEAB2.0-30-15-B-13},{LINA=GEAB2.0-30-15-B-13},{KT=DUMMY},{PN=GEAB2.0-30-15-B-13},{TYPE=GEAB},{SHSALG= 'RH','Round Hole','RHT','Round Hole+Tap','KGH','Key Groove Hole','KGHT','Key Groove Hole+Tap' },{SHALG=1},{MATALG= 'S45C', 'S45C Equivalent', 'SUS304', 'SUS304' },{SHS=RHT},{MAT=S45C},{ST=},{STALG= '','-','BO','Black Oxide','ENP','Electroless Nickel Plating'},{MOD=2.0},{NT=30},{NTA=12,13,14,15,16,17,18,19,20,21,22,23,24,25,26,27,28,29,30,32,33,34,35,36,38,39,40,42,44,45,46,48,49,50,51,52,54,55,56,57,58,60,62,63,64,65,66,68,69,70,72,75,76,77,78,80,81,84,85,88,90,91,92,95,96,98,99,100},{B=15},{TS=B},{TSALG='B','B'},{TSPN=-B},{PS=13},{PSALG='8','8','9','9','10','10','11','11','12','12','13','13','14','14','15','15','16','16','17','17','18','18','19','19','20','20','21','21','22','22','23','23','24','24','25','25','26','26','27','27','28','28','29','29','30','30','31','31','32','32','33','33','34','34','35','35','36','36'},{PS1='8','8','9','9','10','10','11','11','12','12','13','13','14','14','15','15','16','16','17','17','18','18','19','19','20','20','21','21','22','22','23','23','24','24','25','25','26','26','27','27','28','28','29','29','30','30','31','31','32','32','33','33','34','34','35','35','36','36'},{PS2='8N','8N','10N','10N','10K','10K','11N','11N','12N','12N','13N','13N','14N','14N','15N','15N','16N','16N','17N','17N','18N','18N','19N','19N','20N','20N','21N','21N','22N','22N','23N','23N','24N','24N','25N','25N','26N','26N','27N','27N','28N','28N','29N','29N','30N','30N','31N','31N','32N','32N'},{P=13.00},{P2=13},{DD=60},{D=64},{G=55},{H=48},{L=29},{LL1=14},{LL2=7},{M=M6},{M2=6},{M3=6},{ML=17.5},{BB=5},{TT=0},{ALT1=},{ALT1ALG='', 'w/o Set Screw', 'KC90','with KC90 (Set Screw)','KC120','with KC120 (Set Screw)' },{ALT1PN=},{KC=0},{ALT2=},{ALT2ALG= '','w/o TPC (Tapped Hole Dimension)','TPC','with TPC (Tapped Hole Dimension)' },{TPC=N/A},{TPCALG= 'N/A' },{ALT2PN=},{TPC3D=0},{ALT11=},{ALT11ALG= '', 'w/o GBA (Gear bottom adjustment of phase focus)','GBA','with GBA (Gear bottom adjustment of phase focus)' },{ALT11PN=},{DEG=0},{ALT10=},{ALT10ALG= '','w/o BS (Boss Cut)','BS','with BS (Boss Cut)' },{ALT10PN=},{BS=0},{BSALG=0},{BSMIN=9},{BSMAX=14},{ALT4=},{ALT4ALG= '','N/A' },{ALT41=0},{ALT42=0},{ALT4PN=},{Z=0},{ZALG=0},{ZMINL=15},{ZMAXL=51},{ZMINR=15},{ZMAXR=44},{ZPN=},{J=0.0},{JALG=0},{JMIN=2},{JMAX=0},{JPN=},{ALT5=},{ALT5ALG= '','N/A' },{ALT5PN=},{Q=0},{QALG=0},{QMIN=15},{QMAX=44},{QPN=},{R=0},{RALG=0},{RMIN=15},{RMAX=44},{RPN=},{S=0},{SALG=0},{SMIN=3},{SMAX=23},{SPN=},{T=0},{TALG=0},{TMIN=3},{TMAX=0},{TPN=},{ALT9=},{ALT9ALG= '','Not applicable' },{SRG=0.0},{SRGALG=0},{SRGMIN=3.500},{SRGMINALG=3.500},{SRGMAX=0.000},{SRGMAXALG=0.000},{DD2=0.0},{MM=0.00},{NN=0.00},{DD2ALG=0.000},{MMALG=0.000},{NNALG=0.000},{ALT9PN=},{ALT6=},{ALT6ALG= '','N/A' },{LFC=0},{LFCALG=0},{LTC=0},{LTCALG=0},{LPCDMIN=21.000},{LPCDMAX=47.000},{MALT6=N/A},{MALT6ALG= 'N/A' },{C=0.0},{ALT6PN=},{ALT7=},{ALT7ALG= '','w/o Side Through Hole','KFC','with KFC (Side Through Hole)','KTC','with KTC (Side Through Hole)' },{ALT7PN=},{KFC=0},{KFCALG=[0]},{KTCALG=[0]},{KTC=0},{KPCDMIN1=20},{KPCDMAX1=41},{KPCDMIN2=55.000},{KPCDMAX2=48.000},{KPCD=0},{K=0.0},{KALG=[0]},{KALT7L=15},{TIF=2},{SCREW=6},{SCREWL=16},{PLANE=24},{PLANE1=24},{ALT3=},{ALT3ALG= '','w/o Side Tapped Hole','QFC','with QFC (Side Tapped Hole)','QTC','with QTC (Side Tapped Hole)' },{ALT3PN=},{DIRALT3=},{DIRALT3ALG= '','N/A' },{QFC=0},{QFCALG=[0]},{QTC=0},{QTCALG=[0]},{QPCDMIN1=20},{QPCDMAX1=41},{QPCDMIN2=55},{QPCDMAX2=48},{CIFMALT3=3},{QPCD=0},{MALT3=N/A},{MALT3ALG= 'N/A' },{MALT3L=0},{MS1=3},{PITCH=0},{ALT8=},{ALT8ALG= '','w/o Side Counterbored','ZFC','with ZFC (4 Places Side Counterbored)','ZTC','with ZTC (3 Places Side Counterbored)' },{ALT8PN=},{DIRALT8=},{DIRALT8ALG= '','N/A' },{ZFC=0},{ZFCALG=[0]},{ZTC=0},{ZTCALG=[0]},{ZPCDMIN1=23},{ZPCDMIN2=59},{ZPCDMAX1=37},{ZPCDMAX2=44},{ZPCD=0},{U=0},{UALG=[0]},{UMAX=0},{UMAX1=0},{UMAX2=6},{UMIN=3},{U1=0.0},{U2=0.0},{F=0.0},{LL13D=14},{LL23D=22},{LBS=29},{PCD=0},{SHN=0},{SHDEG1=0},{SHDEG2=0},{PZQRDD2=13},{ALT3LBS=28.5},{PPATH=geab20/geab20_asmtpl.prj}")

  mat( 0) = 1.000000
  mat( 1) = 0.000000
  mat( 2) = 0.000000
  mat( 3) = 0.000000
  mat( 4) = 1.000000
  mat( 5) = 0.000000
  mat( 6) = 0.000000
  mat( 7) = 0.000000
  mat( 8) = 1.000000
  mat( 9) = 0.000000
  mat(10) = 0.000000
  mat(11) = 0.000000
  On Error Resume Next

  Set SaveCaseDoc = CATIA.Documents.Item("GEAB2_0_30_15_B_13_b.CATPart")

  If (Err.Number <> 0) Then
    ucaseName = GetUCaseName("GEAB2_0_30_15_B_13_b.CATPart")
    Set SaveCaseDoc = CATIA.Documents.Item(ucaseName)
  End If

  Set newProd = Product.Products.AddComponent(SaveCaseDoc.Product)
  newProd.Move.Apply mat

  NewProd.Name = "tmp_instance_name"
  newInstanceName = GetFirstInstanceName("GEAB2.0-30-15-B-13_b",Product.Products)
  NewProd.Name =  newInstanceName
  NewProd.DescriptionInst =  "Spur Gears - Pressure Angle 20 degree Module 2.0\nGEAHB, GEAHBB, GEAHBG, GEAHS, GEAB, GEABB, GEABG, GEAS, GEAKB, GEAKBB, GEAKBG, GEAKS_2.0_body"

  mat( 0) = 0.000000
  mat( 1) = -1.000000
  mat( 2) = 0.000000
  mat( 3) = 0.000000
  mat( 4) = 0.000000
  mat( 5) = 1.000000
  mat( 6) = -1.000000
  mat( 7) = 0.000000
  mat( 8) = 0.000000
  mat( 9) = 0.000000
  mat(10) = 6.500000
  mat(11) = 22.000000
  On Error Resume Next

  Set SaveCaseDoc = CATIA.Documents.Item("SET_SCREW6_16.CATPart")

  If (Err.Number <> 0) Then
    ucaseName = GetUCaseName("SET_SCREW6_16.CATPart")
    Set SaveCaseDoc = CATIA.Documents.Item(ucaseName)
  End If

  Set newProd = Product.Products.AddComponent(SaveCaseDoc.Product)
  newProd.Move.Apply mat

  NewProd.Name = "tmp_instance_name"
  newInstanceName = GetFirstInstanceName("SET-SCREW6-16",Product.Products)
  NewProd.Name =  newInstanceName
  NewProd.DescriptionInst =  "Set Screw - Flat End\nSET-SCREW"


  Set productDocument1 = CATIA.ActiveDocument
  Set product1 = productDocument1.Product
  Set constraints1 = product1.Connections("CATIAConstraints")
  Set reference1 = product1.CreateReferenceFromName(product1.Name & "/" & product1.Products.Item(1).Name & "/!" & product1.Name & "/" & product1.Products.Item(1).Name & "/")
  Set constraint1 = constraints1.AddMonoEltCst(catCstTypeReference, reference1)
  product1.Update

  Set reference1 = product1.CreateReferenceFromName(product1.Name & "/" & product1.Products.item(1).name & "/!ConnectionBody/LineCoincidence:screw")
  Set reference2 = product1.CreateReferenceFromName(product1.Name & "/" & product1.Products.item(2).name & "/!ConnectionBody/LineCoincidence:CP")
  Set reference3 = product1.CreateReferenceFromName(product1.Name & "/" & product1.Products.item(1).name & "/!ConnectionBody/PlaneOffset:screw")
  Set reference4 = product1.CreateReferenceFromName(product1.Name & "/" & product1.Products.item(2).name & "/!ConnectionBody/PlaneOffset:CP")
  set spaworkbench = CATIA.ActiveDocument.GetWorkbench("SPAWorkbench")
  set anglemeasure = spaworkbench.GetMeasurable(reference1)
  angle = anglemeasure.GetAngleBetween(reference2)
    if angle < 0.001 then
       Set constraint1 = constraints1.AddBiEltCst(catCstTypeOn, reference1, reference2)
       product1.Update
    end if


  Set reference1 = product1.CreateReferenceFromName(product1.Name & "/" & product1.Products.item(1).name & "/!ConnectionBody/LineCoincidence:screw")
  Set reference2 = product1.CreateReferenceFromName(product1.Name & "/" & product1.Products.item(2).name & "/!ConnectionBody/LineCoincidence:CP")
  Set reference3 = product1.CreateReferenceFromName(product1.Name & "/" & product1.Products.item(1).name & "/!ConnectionBody/PlaneAngular:screw")
  Set reference4 = product1.CreateReferenceFromName(product1.Name & "/" & product1.Products.item(2).name & "/!ConnectionBody/PlaneAngular:CP")
  set spaworkbench = CATIA.ActiveDocument.GetWorkbench("SPAWorkbench")
  set anglemeasure = spaworkbench.GetMeasurable(reference1)
  angle = anglemeasure.GetAngleBetween(reference2)
    if angle < 0.001 then
       Set constraint1 = constraints1.AddBiEltCst(catCstTypeOn, reference1, reference2)
       product1.Update
    end if





  On Error Resume Next

  Set SaveCaseDoc = CATIA.Documents.Item("GEAB2_0_30_15_B_13_b.CATPart")

  If (Err.Number <> 0) Then
    ucaseName = GetUCaseName("GEAB2_0_30_15_B_13_b.CATPart")
    Set SaveCaseDoc = CATIA.Documents.Item(ucaseName)
  End If

  SaveCaseDoc.Close

  On Error Resume Next

  Set SaveCaseDoc = CATIA.Documents.Item("SET_SCREW6_16.CATPart")

  If (Err.Number <> 0) Then
    ucaseName = GetUCaseName("SET_SCREW6_16.CATPart")
    Set SaveCaseDoc = CATIA.Documents.Item(ucaseName)
  End If

  SaveCaseDoc.Close
  ProcessDocumentBeforeSave ProductDocument, "GEAB2_0_30_15_B_13.CATProduct"
  Product.Update
  SaveDocument ProductDocument, "GEAB2_0_30_15_B_13.CATProduct"
End Sub

Sub CreatePSolMain()
  On Error Resume Next

  Set PartDocument = CATIA.Documents.Item("GEAB2_0_30_15_B_13.CATProduct")

  If (IsObject(PartDocument)) Then
    PartDocument.Activate
    Exit Sub
  End If

  If (IsEmpty(readSPath)) Then
    Exit Sub
  End If

  Set fso = CreateObject("Scripting.FileSystemObject")

  If (fso.FileExists(storePath & "GEAB2_0_30_15_B_13.CATProduct")) Then
    CATIA.Documents.Open(storePath & "GEAB2_0_30_15_B_13.CATProduct")
    Set fso = Nothing
    Exit Sub
  End If

  Set fso = Nothing

  On Error Goto 0

  CreatePart1
  CreatePart2
  CreateAsm2


End Sub

Sub CATMain()
  CreatePSolMain
End Sub
